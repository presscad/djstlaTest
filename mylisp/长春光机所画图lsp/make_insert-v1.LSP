(defun c:inb()
  (setq bnm "_NBT_cross")
  (if (null (tblsearch "BLOCK" bnm))
	(PROGN
		  (ENTMAKE '((0 . "BLOCK")
			     (8 . "0")
			     (10 0.0 0.0 0.0)
			     (2 . "_NBT_cross")
			     (70 . 2)
			     (1 . "")
			    )
		  )
		  (ENTMAKE '((0 . "LINE")
			     (8 . "0")
			     (67 . 0)
			     (10 0.353553 -0.353553 0.0)
			     (11 -0.353553 0.353553 0.0)
			     (210 0.0 0.0 1.0)
			    )
		  )
		  (ENTMAKE '((0 . "LINE")
			     (8 . "0")
			     (10 -0.353553 -0.353553 0.0)
			     (11 0.353553 0.353553 0.0)
			    )
		  )
		  (ENTMAKE
		    '((0 . "LINE") (8 . "0") (10 0.0 0.0 0.0) (11 -1.0 0.0 0.0))
		  )
	  	;(command "circle" (list 0 0) 5)
	;;;	  (ENTMAKE (list '(0 . "ATTDEF")
	;;;		 (cons 10 '(1 0 0))
	;;;		 (cons 11 '(1 0 0))
	;;;		 (cons 40 1)		 
	;;;		 (cons 1 "0.1")
	;;;		 (cons 3 "0.2")
	;;;		 (cons 2  "heigth") ;height
	;;;		 '(74 . 2)
	;;;		 '(70 . 2))
	;;;	  )
		  (ENTMAKE '((0 . "Endblk")))
		)
    );if (null (tblsearch "BLOCK" bnm))

  	(setq pt(getpoint "\n Please input the insert point:"))
;;;        (entmake (list '(0 . "INSERT")(cons 66 1) (cons 2 "_NBT_cross") (cons 10 (list 0 0))))
  	(entmake (list  '(0 . "INSERT")  (cons  2  "_NBT_cross") (cons 10 pt)))
;;;   	(command "insert" "_NBT_cross" (list 0 0) "" "" "")
  )
