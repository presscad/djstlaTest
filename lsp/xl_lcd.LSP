(defun draw_edge_old ()
  (command "pline"
	   (list -229.75 -195.0)
	   "w"
	   0
	   0
	   (list -230.25 -195.0)
	   (list -230.25 -190.95)
	   (list -230.252 -190.902)
	   (list -230.257 -190.855)
	   (list -230.265 -190.808)
	   (list -230.276 -190.761)
	   (list -230.29 -190.716)
	   (list -230.308 -190.671)
	   (list -230.328 -190.628)
	   (list -230.352 -190.586)
	   (list -230.378 -190.546)
	   (list -230.407 -190.508)
	   (list -230.438 -190.472)
	   (list -230.472 -190.438)
	   (list -230.508 -190.407)
	   (list -230.546 -190.378)
	   (list -230.586 -190.352)
	   (list -230.628 -190.328)
	   (list -230.671 -190.308)
	   (list -230.716 -190.29)
	   (list -230.761 -190.276)
	   (list -230.808 -190.265)
	   (list -230.855 -190.257)
	   (list -230.902 -190.252)
	   (list -230.95 -190.25)
	   (list -235.0 -190.25)
	   (list -235.0 -189.75)
	   (list -230.95 -189.75)
	   (list -230.902 -189.748)
	   (list -230.855 -189.743)
	   (list -230.808 -189.735)
	   (list -230.761 -189.724)
	   (list -230.716 -189.71)
	   (list -230.671 -189.692)
	   (list -230.628 -189.672)
	   (list -230.586 -189.648)
	   (list -230.546 -189.622)
	   (list -230.508 -189.593)
	   (list -230.472 -189.562)
	   (list -230.438 -189.528)
	   (list -230.407 -189.492)
	   (list -230.378 -189.454)
	   (list -230.352 -189.414)
	   (list -230.328 -189.372)
	   (list -230.308 -189.329)
	   (list -230.29 -189.284)
	   (list -230.276 -189.239)
	   (list -230.265 -189.192)
	   (list -230.257 -189.145)
	   (list -230.252 -189.098)
	   (list -230.25 -189.05)
	   (list -230.25 -185.0)
	   (list -229.75 -185.0)
	   (list -229.75 -189.05)
	   (list -229.748 -189.098)
	   (list -229.743 -189.145)
	   (list -229.735 -189.192)
	   (list -229.724 -189.239)
	   (list -229.71 -189.284)
	   (list -229.692 -189.329)
	   (list -229.672 -189.372)
	   (list -229.648 -189.414)
	   (list -229.622 -189.454)
	   (list -229.593 -189.492)
	   (list -229.562 -189.528)
	   (list -229.528 -189.562)
	   (list -229.492 -189.593)
	   (list -229.454 -189.622)
	   (list -229.414 -189.648)
	   (list -229.372 -189.672)
	   (list -229.329 -189.692)
	   (list -229.284 -189.71)
	   (list -229.239 -189.724)
	   (list -229.192 -189.735)
	   (list -229.145 -189.743)
	   (list -229.098 -189.748)
	   (list -229.05 -189.75)
	   (list -225.0 -189.75)
	   (list -225.0 -190.25)
	   (list -229.05 -190.25)
	   (list -229.098 -190.252)
	   (list -229.145 -190.257)
	   (list -229.192 -190.265)
	   (list -229.239 -190.276)
	   (list -229.284 -190.29)
	   (list -229.329 -190.308)
	   (list -229.372 -190.328)
	   (list -229.414 -190.352)
	   (list -229.454 -190.378)
	   (list -229.492 -190.407)
	   (list -229.528 -190.438)
	   (list -229.562 -190.472)
	   (list -229.593 -190.508)
	   (list -229.622 -190.546)
	   (list -229.648 -190.586)
	   (list -229.672 -190.628)
	   (list -229.692 -190.671)
	   (list -229.71 -190.716)
	   (list -229.724 -190.761)
	   (list -229.735 -190.808)
	   (list -229.743 -190.855)
	   (list -229.748 -190.902)
	   (list -229.75 -190.95)
	   "c"
  )
  (command "pline"
	   (list -229.75 185.0)
	   "w"
	   0
	   0
	   (list -230.25 185.0)
	   (list -230.25 189.05)
	   (list -230.252 189.098)
	   (list -230.257 189.145)
	   (list -230.265 189.192)
	   (list -230.276 189.239)
	   (list -230.29 189.284)
	   (list -230.308 189.329)
	   (list -230.328 189.372)
	   (list -230.352 189.414)
	   (list -230.378 189.454)
	   (list -230.407 189.492)
	   (list -230.438 189.528)
	   (list -230.472 189.562)
	   (list -230.508 189.593)
	   (list -230.546 189.622)
	   (list -230.586 189.648)
	   (list -230.628 189.672)
	   (list -230.671 189.692)
	   (list -230.716 189.71)
	   (list -230.761 189.724)
	   (list -230.808 189.735)
	   (list -230.855 189.743)
	   (list -230.902 189.748)
	   (list -230.95 189.75)
	   (list -235.0 189.75)
	   (list -235.0 190.25)
	   (list -230.95 190.25)
	   (list -230.902 190.252)
	   (list -230.855 190.257)
	   (list -230.808 190.265)
	   (list -230.761 190.276)
	   (list -230.716 190.29)
	   (list -230.671 190.308)
	   (list -230.628 190.328)
	   (list -230.586 190.352)
	   (list -230.546 190.378)
	   (list -230.508 190.407)
	   (list -230.472 190.438)
	   (list -230.438 190.472)
	   (list -230.407 190.508)
	   (list -230.378 190.546)
	   (list -230.352 190.586)
	   (list -230.328 190.628)
	   (list -230.308 190.671)
	   (list -230.29 190.716)
	   (list -230.276 190.761)
	   (list -230.265 190.808)
	   (list -230.257 190.855)
	   (list -230.252 190.902)
	   (list -230.25 190.95)
	   (list -230.25 195.0)
	   (list -229.75 195.0)
	   (list -229.75 190.95)
	   (list -229.748 190.902)
	   (list -229.743 190.855)
	   (list -229.735 190.808)
	   (list -229.724 190.761)
	   (list -229.71 190.716)
	   (list -229.692 190.671)
	   (list -229.672 190.628)
	   (list -229.648 190.586)
	   (list -229.622 190.546)
	   (list -229.593 190.508)
	   (list -229.562 190.472)
	   (list -229.528 190.438)
	   (list -229.492 190.407)
	   (list -229.454 190.378)
	   (list -229.414 190.352)
	   (list -229.372 190.328)
	   (list -229.329 190.308)
	   (list -229.284 190.29)
	   (list -229.239 190.276)
	   (list -229.192 190.265)
	   (list -229.145 190.257)
	   (list -229.098 190.252)
	   (list -229.05 190.25)
	   (list -225.0 190.25)
	   (list -225.0 189.75)
	   (list -229.05 189.75)
	   (list -229.098 189.748)
	   (list -229.145 189.743)
	   (list -229.192 189.735)
	   (list -229.239 189.724)
	   (list -229.284 189.71)
	   (list -229.329 189.692)
	   (list -229.372 189.672)
	   (list -229.414 189.648)
	   (list -229.454 189.622)
	   (list -229.492 189.593)
	   (list -229.528 189.562)
	   (list -229.562 189.528)
	   (list -229.593 189.492)
	   (list -229.622 189.454)
	   (list -229.648 189.414)
	   (list -229.672 189.372)
	   (list -229.692 189.329)
	   (list -229.71 189.284)
	   (list -229.724 189.239)
	   (list -229.735 189.192)
	   (list -229.743 189.145)
	   (list -229.748 189.098)
	   (list -229.75 189.05)
	   "c"
  )
  (command "pline"
	   (list 290.0 220.0)
	   "w"
	   0
	   0
	   (list 275.0 220.0)
	   (list 265.0 220.0)
	   (list 265.0 222.0)
	   (list 275.0 222.0)
	   (list 292.0 222.0)
	   (list 292.0 -222.0)
	   (list 275.0 -222.0)
	   (list 265.0 -222.0)
	   (list 265.0 -220.0)
	   (list 275.0 -220.0)
	   (list 290.0 -220.0)
	   "c"
  )
  (command "pline"
	   (list 240.0 -222.0)
	   "w"
	   0
	   0
	   (list 180.0 -222.0)
	   (list 180.0 -220.0)
	   (list 240.0 -220.0)
	   "c"
  )
  (command "pline"
	   (list 240.0 220.0)
	   "w"
	   0
	   0
	   (list 180.0 220.0)
	   (list 180.0 222.0)
	   (list 240.0 222.0)
	   "c"
  )
  (command "pline"
	   (list -292.0 222.0)
	   "w"
	   0
	   0
	   (list -275.0 222.0)
	   (list -265.0 222.0)
	   (list -265.0 220.0)
	   (list -275.0 220.0)
	   (list -290.0 220.0)
	   (list -290.0 -220.0)
	   (list -275.0 -220.0)
	   (list -265.0 -220.0)
	   (list -265.0 -222.0)
	   (list -275.0 -222.0)
	   (list -292.0 -222.0)
	   "c"
  )
  (command "pline"
	   (list -240.0 -222.0)
	   "w"
	   0
	   0
	   (list -180.0 -222.0)
	   (list -180.0 -220.0)
	   (list -240.0 -220.0)
	   "c"
  )
  (command "pline"
	   (list -240.0 220.0)
	   "w"
	   0
	   0
	   (list -180.0 220.0)
	   (list -180.0 222.0)
	   (list -240.0 222.0)
	   "c"
  )
  (command "pline"
	   (list 235.0 190.25)
	   "w"
	   0
	   0
	   (list 225.0 190.25)
	   (list 225.0 189.75)
	   (list 235.0 189.75)
	   "c"
  )
  (command "pline"
	   (list 235.0 -190.25)
	   "w"
	   0
	   0
	   (list 225.0 -190.25)
	   (list 225.0 -189.75)
	   (list 235.0 -189.75)
	   "c"
  )
)
(defun draw_edge_new ()
  (command "pline"
	   (list -259.75 -215.0)
	   "w"
	   0
	   0
	   (list -260.25 -215.0)
	   (list -260.25 -210.95)
	   (list -260.252 -210.902)
	   (list -260.257 -210.855)
	   (list -260.265 -210.808)
	   (list -260.276 -210.761)
	   (list -260.29 -210.716)
	   (list -260.308 -210.671)
	   (list -260.328 -210.628)
	   (list -260.352 -210.586)
	   (list -260.378 -210.546)
	   (list -260.407 -210.508)
	   (list -260.438 -210.472)
	   (list -260.472 -210.438)
	   (list -260.508 -210.407)
	   (list -260.546 -210.378)
	   (list -260.586 -210.352)
	   (list -260.628 -210.328)
	   (list -260.671 -210.308)
	   (list -260.716 -210.29)
	   (list -260.761 -210.276)
	   (list -260.808 -210.265)
	   (list -260.855 -210.257)
	   (list -260.902 -210.252)
	   (list -260.95 -210.25)
	   (list -265.0 -210.25)
	   (list -265.0 -209.75)
	   (list -260.95 -209.75)
	   (list -260.902 -209.748)
	   (list -260.855 -209.743)
	   (list -260.808 -209.735)
	   (list -260.761 -209.724)
	   (list -260.716 -209.71)
	   (list -260.671 -209.692)
	   (list -260.628 -209.672)
	   (list -260.586 -209.648)
	   (list -260.546 -209.622)
	   (list -260.508 -209.593)
	   (list -260.472 -209.562)
	   (list -260.438 -209.528)
	   (list -260.407 -209.492)
	   (list -260.378 -209.454)
	   (list -260.352 -209.414)
	   (list -260.328 -209.372)
	   (list -260.308 -209.329)
	   (list -260.29 -209.284)
	   (list -260.276 -209.239)
	   (list -260.265 -209.192)
	   (list -260.257 -209.145)
	   (list -260.252 -209.098)
	   (list -260.25 -209.05)
	   (list -260.25 -205.0)
	   (list -259.75 -205.0)
	   (list -259.75 -209.05)
	   (list -259.748 -209.098)
	   (list -259.743 -209.145)
	   (list -259.735 -209.192)
	   (list -259.724 -209.239)
	   (list -259.71 -209.284)
	   (list -259.692 -209.329)
	   (list -259.672 -209.372)
	   (list -259.648 -209.414)
	   (list -259.622 -209.454)
	   (list -259.593 -209.492)
	   (list -259.562 -209.528)
	   (list -259.528 -209.562)
	   (list -259.492 -209.593)
	   (list -259.454 -209.622)
	   (list -259.414 -209.648)
	   (list -259.372 -209.672)
	   (list -259.329 -209.692)
	   (list -259.284 -209.71)
	   (list -259.239 -209.724)
	   (list -259.192 -209.735)
	   (list -259.145 -209.743)
	   (list -259.098 -209.748)
	   (list -259.05 -209.75)
	   (list -255.0 -209.75)
	   (list -255.0 -210.25)
	   (list -259.05 -210.25)
	   (list -259.098 -210.252)
	   (list -259.145 -210.257)
	   (list -259.192 -210.265)
	   (list -259.239 -210.276)
	   (list -259.284 -210.29)
	   (list -259.329 -210.308)
	   (list -259.372 -210.328)
	   (list -259.414 -210.352)
	   (list -259.454 -210.378)
	   (list -259.492 -210.407)
	   (list -259.528 -210.438)
	   (list -259.562 -210.472)
	   (list -259.593 -210.508)
	   (list -259.622 -210.546)
	   (list -259.648 -210.586)
	   (list -259.672 -210.628)
	   (list -259.692 -210.671)
	   (list -259.71 -210.716)
	   (list -259.724 -210.761)
	   (list -259.735 -210.808)
	   (list -259.743 -210.855)
	   (list -259.748 -210.902)
	   (list -259.75 -210.95)
	   "c"
  )
  (command "pline"
	   (list -259.75 205.0)
	   "w"
	   0
	   0
	   (list -260.25 205.0)
	   (list -260.25 209.05)
	   (list -260.252 209.098)
	   (list -260.257 209.145)
	   (list -260.265 209.192)
	   (list -260.276 209.239)
	   (list -260.29 209.284)
	   (list -260.308 209.329)
	   (list -260.328 209.372)
	   (list -260.352 209.414)
	   (list -260.378 209.454)
	   (list -260.407 209.492)
	   (list -260.438 209.528)
	   (list -260.472 209.562)
	   (list -260.508 209.593)
	   (list -260.546 209.622)
	   (list -260.586 209.648)
	   (list -260.628 209.672)
	   (list -260.671 209.692)
	   (list -260.716 209.71)
	   (list -260.761 209.724)
	   (list -260.808 209.735)
	   (list -260.855 209.743)
	   (list -260.902 209.748)
	   (list -260.95 209.75)
	   (list -265.0 209.75)
	   (list -265.0 210.25)
	   (list -260.95 210.25)
	   (list -260.902 210.252)
	   (list -260.855 210.257)
	   (list -260.808 210.265)
	   (list -260.761 210.276)
	   (list -260.716 210.29)
	   (list -260.671 210.308)
	   (list -260.628 210.328)
	   (list -260.586 210.352)
	   (list -260.546 210.378)
	   (list -260.508 210.407)
	   (list -260.472 210.438)
	   (list -260.438 210.472)
	   (list -260.407 210.508)
	   (list -260.378 210.546)
	   (list -260.352 210.586)
	   (list -260.328 210.628)
	   (list -260.308 210.671)
	   (list -260.29 210.716)
	   (list -260.276 210.761)
	   (list -260.265 210.808)
	   (list -260.257 210.855)
	   (list -260.252 210.902)
	   (list -260.25 210.95)
	   (list -260.25 215.0)
	   (list -259.75 215.0)
	   (list -259.75 210.95)
	   (list -259.748 210.902)
	   (list -259.743 210.855)
	   (list -259.735 210.808)
	   (list -259.724 210.761)
	   (list -259.71 210.716)
	   (list -259.692 210.671)
	   (list -259.672 210.628)
	   (list -259.648 210.586)
	   (list -259.622 210.546)
	   (list -259.593 210.508)
	   (list -259.562 210.472)
	   (list -259.528 210.438)
	   (list -259.492 210.407)
	   (list -259.454 210.378)
	   (list -259.414 210.352)
	   (list -259.372 210.328)
	   (list -259.329 210.308)
	   (list -259.284 210.29)
	   (list -259.239 210.276)
	   (list -259.192 210.265)
	   (list -259.145 210.257)
	   (list -259.098 210.252)
	   (list -259.05 210.25)
	   (list -255.0 210.25)
	   (list -255.0 209.75)
	   (list -259.05 209.75)
	   (list -259.098 209.748)
	   (list -259.145 209.743)
	   (list -259.192 209.735)
	   (list -259.239 209.724)
	   (list -259.284 209.71)
	   (list -259.329 209.692)
	   (list -259.372 209.672)
	   (list -259.414 209.648)
	   (list -259.454 209.622)
	   (list -259.492 209.593)
	   (list -259.528 209.562)
	   (list -259.562 209.528)
	   (list -259.593 209.492)
	   (list -259.622 209.454)
	   (list -259.648 209.414)
	   (list -259.672 209.372)
	   (list -259.692 209.329)
	   (list -259.71 209.284)
	   (list -259.724 209.239)
	   (list -259.735 209.192)
	   (list -259.743 209.145)
	   (list -259.748 209.098)
	   (list -259.75 209.05)
	   "c"
  )
  (command "pline"
	   (list 265.0 -210.25)
	   "w"
	   0
	   0
	   (list 255.0 -210.25)
	   (list 255.0 -209.75)
	   (list 265.0 -209.75)
	   "c"
  )
  (command "pline"
	   (list 5.0 -210.25)
	   "w"
	   0
	   0
	   (list -5.0 -210.25)
	   (list -5.0 -209.75)
	   (list 5.0 -209.75)
	   "c"
  )
  (command "pline"
	   (list 265.0 210.25)
	   "w"
	   0
	   0
	   (list 255.0 210.25)
	   (list 255.0 209.75)
	   (list 265.0 209.75)
	   "c"
  )
  (command "pline"
	   (list 5.0 210.25)
	   "w"
	   0
	   0
	   (list -5.0 210.25)
	   (list -5.0 209.75)
	   (list 5.0 209.75)
	   "c"
  )
  (command "pline"
	   (list -310.0 232.0)
	   "w"
	   0
	   0
	   (list -310.0 230.0)
	   (list -325.0 230.0)
	   (list -325.0 -230.0)
	   (list -310.0 -230.0)
	   (list -310.0 -232.0)
	   (list -327.0 -232.0)
	   (list -327.0 232.0)
	   "c"
  )
  (command "pline"
	   (list 280.0 -232.0)
	   "w"
	   0
	   0
	   (list 280.0 -230.0)
	   (list -280.0 -230.0)
	   (list -280.0 -232.0)
	   "c"
  )
  (command "pline"
	   (list 280.0 232.0)
	   "w"
	   0
	   0
	   (list -280.0 232.0)
	   (list -280.0 230.0)
	   (list 280.0 230.0)
	   "c"
  )
  (command "pline"
	   (list 310.0 232.0)
	   "w"
	   0
	   0
	   (list 327.0 232.0)
	   (list 327.0 -232.0)
	   (list 310.0 -232.0)
	   (list 310.0 -230.0)
	   (list 325.0 -230.0)
	   (list 325.0 230.0)
	   (list 310.0 230.0)
	   "c"
  )
  (command "circle" "-319,-225" "1.5")
  (command "circle" "-319,-200" "1.5")
  (command "circle" "-319,-125" "1")
  (command "circle" "-319,-100" "1.5")
  (command "circle" "-319,-75" "1")
  (command "circle" "-319,0" "1.5")
  (command "circle" "-319,225" "1.5")
  (command "circle" "-319,200" "1.5")
  (command "circle" "-319,125" "1")
  (command "circle" "-319,100" "1.5")
  (command "circle" "-319,75" "1")
  (command "circle" "319,-225" "1.5")
  (command "circle" "319,-200" "1.5")
  (command "circle" "319,-125" "1")
  (command "circle" "319,-100" "1.5")
  (command "circle" "319,-75" "1")
  (command "circle" "319,0" "1.5")
  (command "circle" "319,225" "1.5")
  (command "circle" "319,200" "1.5")
  (command "circle" "319,125" "1")
  (command "circle" "319,100" "1.5")
  (command "circle" "319,75" "1")
)
(defun scale (layer_name ke)
  (command "zoom" "E")
  (setq
    ss_lwpl (ssget "x"
		   (list (cons 0 "lwpolyline") (cons 8 layer_name))
	    )
  )
  (if ss_lwpl
    (progn
      (setq ss_cnt (sslength ss_lwpl))
      (setq i_loop 0)
      (while (< i_loop ss_cnt)
	(setq pl_dt (entget (ssname ss_lwpl i_loop)))
	(setq dt nil)
	(while pl_dt
	  (if (/= (caar pl_dt) 10)
	    (setq dt (append dt (list (car pl_dt))))
	    (progn
	      (setq scl_x (* (cadar pl_dt) ke))
	      (setq scl_y (caddar pl_dt))
	      (setq
		dt (append dt (list (cons 10 (list scl_x scl_y 0))))
	      )
	    )
	  )
	  (setq pl_dt (cdr pl_dt))
	)
	(entmod dt)
	(setq i_loop (1+ i_loop))
      )
    )
  )
  (setq
      ss_lwpl (ssget "x"
		     (list (cons 0 "CIRCLE") (cons 8 layer_name))
	      )
    )
	(if	ss_lwpl
      (progn
	(setq ss_cnt (sslength ss_lwpl))
	(setq i_loop 0)
	(while (< i_loop ss_cnt)
	  (setq pl_dt (entget (ssname ss_lwpl i_loop)))
	  (setq center (cdr (assoc 10 pl_dt)))
	  (setq center (list (* ke (car center)) ( cadr center)))	  
	  (setq pl_dt (subst (cons 10 center) (assoc 10 pl_dt) pl_dt))
	  (entmod pl_dt)
	  (setq i_loop (1+ i_loop))
	)
     )
  )
  (command "zoom" "E")

)
(defun ofst (layer_name cf1 ce1)
  (command "zoom" "E")
  (setq
    ss_lwpl (ssget "x"
		   (list (cons 0 "lwpolyline") (cons 8 layer_name))
	    )
  )
  (if ss_lwpl
    (progn
      (setq ss_cnt (sslength ss_lwpl))
      (setq i_loop 0)
      (while (< i_loop ss_cnt)
	(setq pl_dt (entget (ssname ss_lwpl i_loop)))
	(setq cx 0)
	(setq cy 0)
	(setq cnt 0)
	(setq dt pl_dt)
	(while pl_dt
	  (if (= (caar pl_dt) 10)
	    (progn
	      (setq cx (+ (cadar pl_dt) cx))
	      (setq cy (+ (caddar pl_dt) cy))
	      (setq cnt (1+ cnt))
	    )
	  )
	  (setq pl_dt (cdr pl_dt))
	)
	(setq cx (/ cx cnt))
	(setq cy (/ cy cnt))
	(setq pl_dt dt)
	(setq dt nil)
	(while pl_dt
	  (if (/= (caar pl_dt) 10)
	    (setq dt (append dt (list (car pl_dt))))
	    (progn
	      (setq ofst_x (cadar pl_dt))
	      (setq ofst_y (caddar pl_dt))
	      (if (> ofst_x cx)
		(setq ofst_x (- ofst_x cf1))
		(setq ofst_x (+ ofst_x cf1))
	      )
	      (if (> ofst_y cy)
		(setq ofst_y (- ofst_y ce1))
		(setq ofst_y (+ ofst_y ce1))
	      )
	      (setq dt
		     (append dt (list (cons 10 (list ofst_x ofst_y 0))))
	      )
	    )
	  )
	  (setq pl_dt (cdr pl_dt))
	)
	(entmod dt)
	(setq i_loop (1+ i_loop))
      )
    )
  )
)
(defun c:xl (/		input_o_n  ito_point  ito_pointx ito_pointy
	     ito_center	ss_txt	   txt_len    i		 txt_table
	     txt_con	txt_l	   txt_ke     ke	 ce1
	     cf1	ss1	   cells      ss2	 ss_txt
	    )
  (command "layer" "u" "*" "")
  (command "layer" "t" "*" "")
  (setvar "osmode" 1)
  (setq input_o_n (getstring "请问是旧机(二厂)或是新机(五厂)<Old/New/Enter>"))
  (if (or (equal (strcase input_o_n) "O")
	  (equal (strcase input_o_n) "OLD")
      )
    (progn
      (setq ito_point (getpoint "/n请点取凸版ITO的左下角:"))
      (setvar "osmode" 0)
      
      (setq ito_pointx (car ito_point))
      (setq ito_pointy (cadr ito_point))
      (setq ito_center (list (+ ito_pointx 200) (+ ito_pointy 185)))
      (command "move" "all" "" ito_center "0,0")
      (command "zoom" "e" "")
      (setq
	ss_txt (ssget "w"
		      '(-290 -220)
		      '(290 220)
		      (list (cons 0 "text"))
	       )
      )
      (setq txt_len (sslength ss_txt))
      (setq i 0)
      (while (< i txt_len)
	(setq txt_table (entget (ssname ss_txt i)))
	(setq txt_con (cdr (assoc 1 txt_table)))
	(setq txt_l (strlen txt_con))
	(while (>= txt_l 6)
	  (setq txt_ke (substr txt_con 1 6))

	  (if (equal txt_ke "0.9825")
	    (progn
	      (setq ke 1.000712)
	      (setq ce1 0.025)
	      (setq cf1 0.025)
	    )
	  )
	  (if (equal txt_ke "0.9822")

	    (progn
	      (setq ke 1.00102)
	      (setq ce1 0.025)
	      (setq cf1 0.025)
	    )
	  )
	  (setq txt_con (substr txt_con 2))
	  (setq txt_l (strlen txt_con))
	)
	(setq i (+ i 1))
      )

      (command "zoom" "e" "")
      (setq ss1 (ssget "c" '(-199 -184) '(199 184)))
      (command "layer" "n" "scal" "")
      (command "change" ss1 "" "p" "la" "scal" "")
      (scale "scal" ke)
      (command "layer" "n" "ofst" "")
      (prompt "/n请选中所有单粒！")
      (setq cells (ssget))
      (command "change" cells "" "p" "la" "ofst" "")
      (ofst "ofst" cf1 ce1)
      (command "layer" "n" "ok" "")
      (setq ss2 (ssget "c" '(-199 -184) '(199 184)))
      (command "change" ss2 "" "p" "la" "ok" "")
      (command "change" ss_txt "" "p" "la" "ok" "")
      (command "layer" "lo" "ok" "")
      (command "erase" "all" "")
      (command "layer" "m" "ok" "")
      (command "layer" "u" "ok" "")
      (command "purge" "all" "" "n")
      (draw_edge_old)
      (setq flag 1)
    )
    (progn
      (setq ito_point (getpoint "/n请点取凸版ITO的左下角:"))
      (setvar "osmode" 0)
      
      (setq ito_pointx (car ito_point))
      (setq ito_pointy (cadr ito_point))
      (setq ito_center (list (+ ito_pointx 235) (+ ito_pointy 185)))
      (command "move" "all" "" ito_center "0,0")
      (command "zoom" "e" "")
      (setq
	ss_txt (ssget "w"
		      '(-325 -230)
		      '(325 230)
		      (list (cons 0 "text"))
	       )
      )
      (setq txt_len (sslength ss_txt))
      (setq i 0)
      (while (< i txt_len)
	(setq txt_table (entget (ssname ss_txt i)))
	(setq txt_con (cdr (assoc 1 txt_table)))
	(setq txt_l (strlen txt_con))
	(while (>= txt_l 6)
	  (setq txt_ke (substr txt_con 1 6))

	  (if (equal txt_ke "0.9825")
	    (progn
	      (setq ke 1.0061)
	      (setq ce1 0)
	      (setq cf1 0)
	    )
	  )

	  (setq txt_con (substr txt_con 2))
	  (setq txt_l (strlen txt_con))
	)
	(setq i (+ i 1))
      )

      (command "zoom" "e" "")
      (setq ss1 (ssget "c" '(-234 -184) '(234 184)))
      (command "layer" "n" "scal" "")
      (command "change" ss1 "" "p" "la" "scal" "")
      (scale "scal" ke)
      (command "layer" "n" "ofst" "")
      (prompt "/n请选中所有单粒！")
      (setq cells (ssget))
      (command "change" cells "" "p" "la" "ofst" "")
      (ofst "ofst" cf1 ce1)
      (command "layer" "n" "ok" "")
      (setq ss2 (ssget "c" '(-234 -184) '(234 184)))
      (command "change" ss2 "" "p" "la" "ok" "")
      (command "change" ss_txt "" "p" "la" "ok" "")
      (command "layer" "lo" "ok" "")
      (command "erase" "all" "")
      (command "layer" "m" "ok" "")
      (command "layer" "u" "ok" "")
      (command "purge" "all" "" "n")
      (draw_edge_new)
      (setq flag 1)
    )
  )


  (setq ss_txt (ssget "x" (list (cons 0 "TEXT"))))
  (setq s_len (sslength ss_txt))
  (setq i 0)
  (while (< i txt_len)
    (setq txt_table (entget (ssname ss_txt i)))
    (setq txt_con (cdr (assoc 1 txt_table)))
    (setq apr_id txt_con)
    (setq txt_l (strlen txt_con))
    (while (>= txt_l 6)
      (setq txt_ke (substr txt_con 1 6))
      (if (or (equal txt_ke "0.9825")
	      (equal txt_ke "0.9822")
	  )
	(progn
	  (setq c_date (getvar "CDATE"))
	  (setq apr_id (strcat apr_id " QINGYI " (itoa (fix c_date))))
	  (setq apr_id (strcase apr_id))
	  (setq	txt_dt
		 (subst (cons 1 apr_id) (assoc 1 txt_table) txt_table)
	  )
	  (entmod txt_dt)
	)
      )
      (setq txt_con (substr txt_con 2))
      (setq txt_l (strlen txt_con))
    )
    (setq i (+ i 1))
  )
  (command "change" "all" "" "p" "la" "0" "")
  (command "layer" "m" "0" "")
  (command "purge" "all" "" "n")

  (getstring
    (strcat "2005-06-21 modified by XifengCheng　！请确认系数是：Ke="
	    (rtos ke)
	    "; Ce="
	    (rtos (* 2 ce1))
	    "; Cf="
	    (rtos (* 2 cf1))
	    
    )
  )
  (if (or (equal (strcase input_o_n) "O")
	  (equal (strcase input_o_n) "OLD")
      )

    (getstring "------此版为旧机(信利二厂)------")
    (getstring "------此版为新机(信利五厂)------")
  )
  )
(PROMPT "\n 输入 XL 运行程序")
