(defun c:dd()
  (defun get_dt_vl (item dt)
  (cdr (assoc item dt))
)
  (setq line_ss (ssget "x" (list (cons 0 "line"))))
  (while (> (sslength ss) 0)
    (setq dt (entget (ssname ss 0)))
    (setq ss (ssdel (ssname ss 0) ss))
    (setq x1 (car (get_dt_vl 10)))
    (setq x2 (car (get_dt_vl 11)))
    (if (equal x1 x2 0.0001)
      (progn
	(setq dt (subst (cons 8 "del") (assoc 8 dt) dt))
	(entmod dt)
	)

      )
    )
  )
