(defun draw_edge () 
        (command "pline" (list 207.9 268.15) "w" 0 0 
                         (list 207.9 264.9) 
                         (list 206.4 264.9) 
                         (list 206.4 268.15) 
                         (list 203.15 268.15) 
                         (list 203.15 269.65) 
                         (list 206.4 269.65) 
                         (list 206.4 272.9) 
                         (list 207.9 272.9) 
                         (list 207.9 269.65) 
                         (list 211.15 269.65) 
                         (list 211.15 268.15) 
                         "c"
         )
        (command "pline" (list 200.9 273.1) "w" 0 0 
                         (list 203.4 273.1) 
                         (list 203.4 272.1) 
                         (list 200.9 272.1) 
                         (list 200.9 269.6) 
                         (list 199.9 269.6) 
                         (list 199.9 272.1) 
                         (list 197.4 272.1) 
                         (list 197.4 273.1) 
                         (list 199.9 273.1) 
                         (list 199.9 275.6) 
                         (list 200.9 275.6) 
                         "c"
         )
        (command "pline" (list 207.9 -204.2) "w" 0 0 
                         (list 207.9 -207.45) 
                         (list 206.4 -207.45) 
                         (list 206.4 -204.2) 
                         (list 203.15 -204.2) 
                         (list 203.15 -202.7) 
                         (list 206.4 -202.7) 
                         (list 206.4 -199.45) 
                         (list 207.9 -199.45) 
                         (list 207.9 -202.7) 
                         (list 211.15 -202.7) 
                         (list 211.15 -204.2) 
                         "c"
         )
        (command "pline" (list -214.0 344.2) "w" 0 0 
                         (list -214.0 319.2) 
                         (list -212.0 319.2) 
                         (list -212.0 342.2) 
                         (list 212.0 342.2) 
                         (list 212.0 319.2) 
                         (list 214.0 319.2) 
                         (list 214.0 344.2) 
                         "c"
         )
        (command "pline" (list 214.0 -277.8) "w" 0 0 
                         (list 214.0 -252.8) 
                         (list 212.0 -252.8) 
                         (list 212.0 -275.8) 
                         (list -212.0 -275.8) 
                         (list -212.0 -252.8) 
                         (list -214.0 -252.8) 
                         (list -214.0 -277.8) 
                         "c"
         )
        (command "pline" (list -214.0 -222.8) "w" 0 0 
                         (list -212.0 -222.8) 
                         (list -212.0 279.2) 
                         (list -214.0 279.2) 
                         "c"
         )
        (command "pline" (list 212.0 279.2) "w" 0 0 
                         (list 214.0 279.2) 
                         (list 214.0 -222.8) 
                         (list 212.0 -222.8) 
                         "c"
         )
        (command "pline" (list -200.9 273.1) "w" 0 0 
                         (list -203.4 273.1) 
                         (list -203.4 272.1) 
                         (list -200.9 272.1) 
                         (list -200.9 269.6) 
                         (list -199.9 269.6) 
                         (list -199.9 272.1) 
                         (list -197.4 272.1) 
                         (list -197.4 273.1) 
                         (list -199.9 273.1) 
                         (list -199.9 275.6) 
                         (list -200.9 275.6) 
                         "c"
         )
        (command "pline" (list -207.9 268.15) "w" 0 0 
                         (list -207.9 264.9) 
                         (list -206.4 264.9) 
                         (list -206.4 268.15) 
                         (list -203.15 268.15) 
                         (list -203.15 269.65) 
                         (list -206.4 269.65) 
                         (list -206.4 272.9) 
                         (list -207.9 272.9) 
                         (list -207.9 269.65) 
                         (list -211.15 269.65) 
                         (list -211.15 268.15) 
                         "c"
         )
        (command "pline" (list -207.9 -204.2) "w" 0 0 
                         (list -207.9 -207.45) 
                         (list -206.4 -207.45) 
                         (list -206.4 -204.2) 
                         (list -203.15 -204.2) 
                         (list -203.15 -202.7) 
                         (list -206.4 -202.7) 
                         (list -206.4 -199.45) 
                         (list -207.9 -199.45) 
                         (list -207.9 -202.7) 
                         (list -211.15 -202.7) 
                         (list -211.15 -204.2) 
                         "c"
         )
      (command "circle" "-200,335.2""1.5")
      (command "circle" "-175,335.2""1.5")
      (command "circle" "-87.5,335.2""1.5")
      (command "circle" "0,335.2""1.5")
      (command "circle" "87.5,335.2""1.5")
      (command "circle" "175,335.2""1.5")
      (command "circle" "200,335.2""1.5")
      (command "circle" "-200,-268.8""1.5")
      (command "circle" "-175,-268.8""1.5")
      (command "circle" "-87.5,-268.8""1.5")
      (command "circle" "0,-268.8""1.5")
      (command "circle" "87.5,-268.8""1.5")
      (command "circle" "175,-268.8""1.5")
      (command "circle" "200,-268.8""1.5")
  )
  
(defun scale (layer_name ke)
    (command "zoom" "E")
    (setq
      ss_lwpl (ssget "x"
		     (list (cons 0 "lwpolyline") (cons 8 layer_name))
	      )
    )
    (if	ss_lwpl
      (progn
	(setq ss_cnt (sslength ss_lwpl))
	(setq i_loop 0)
	(while (< i_loop ss_cnt)
	  (setq pl_dt (entget (ssname ss_lwpl i_loop)))
	  (setq dt nil)
	  (while pl_dt
	    (if	(/= (caar pl_dt) 10)
	      (setq dt (append dt (list (car pl_dt))))
	      (progn
		(setq scl_x (cadar pl_dt))
		(setq scl_y (* (caddar pl_dt) ke))
		(setq
		  dt (append dt (list (cons 10 (list scl_x scl_y 0))))
		)
	      )
	    )
	    (setq pl_dt (cdr pl_dt))
	  )
	  (entmod dt)
	  (setq i_loop (1+ i_loop))
      )
    ))
    (command "zoom" "E")
    
  )   ;        defun scale(layer_name ke)                                                          




(defun ofst (layer_name cf1 ce1)
    (command "zoom" "E")
    (setq
      ss_lwpl (ssget "x"
		     (list (cons 0 "lwpolyline") (cons 8 layer_name))
	      )
    )
    (if	ss_lwpl
      (progn
	(setq ss_cnt (sslength ss_lwpl))
	(setq i_loop 0)
	(while (< i_loop ss_cnt)
	  (setq pl_dt (entget (ssname ss_lwpl i_loop)))
	  (setq cx 0)
	  (setq cy 0)
	  (setq cnt 0)
	  (setq dt pl_dt)
	  (while pl_dt
	    (if	(= (caar pl_dt) 10)
	      (progn
		(setq cx (+ (cadar pl_dt) cx))
		(setq cy (+ (caddar pl_dt) cy))
		(setq cnt (1+ cnt))
	      )
	    )
	    (setq pl_dt (cdr pl_dt))
	  )
	  (setq cx (/ cx cnt))
	  (setq cy (/ cy cnt))
	  (setq pl_dt dt)
	  (setq dt nil)
	  (while pl_dt
	    (if	(/= (caar pl_dt) 10)
	      (setq dt (append dt (list (car pl_dt))))
	      (progn
		(setq ofst_x (cadar pl_dt))
		(setq ofst_y (caddar pl_dt))
		(if (> ofst_x cx)
		  (setq ofst_x (- ofst_x cf1))
		  (setq ofst_x (+ ofst_x cf1))
		)
		(if (> ofst_y cy)
		  (setq ofst_y (- ofst_y ce1))
		  (setq ofst_y (+ ofst_y ce1))
		)
		(setq dt
		       (append dt (list (cons 10 (list ofst_x ofst_y 0))))
		)
	      )
	    )
	    (setq pl_dt (cdr pl_dt))
	  )
	  (entmod dt)
	  (setq i_loop (1+ i_loop))
	)
      )
    )
  )
(defun a_cell()
  (prompt "/n 对单粒进行排版：")
  (setq colu_num (getreal "\n请输入X方向排版个数:"))
  (setq row_num (getreal"\n 请输入Y方向排版个数:"))
  (setq colu_dis (getreal "\n 请输入X方向的排版步距:"))
  (setq row_dis (getreal "\n 请输入Y方向的排版步距:"))
  (setq pandun (getstring "单粒的排版个数一样吗？　(Yes/NO<N>)　"))
  (if (= (strcase pandun) "Y" )
  (progn
  (prompt "/n请选择凸块")
  (setq scell4 (ssget))
  (command "array" scell4 """" (fix row_num) (fix colu_num) row_dis colu_dis "" "")
   )
 )
   (if (= (strcase pandun) "N" )
   (progn
   (setq XY (getstring "是X　还是　Y　方向的排版不一样　"))
   (if(= (strcase XY) "X")
   (progn (setq colu_num1 (+ 0.5 colu_num))
          (fix colu_num1) (fix colu_num) (fix row_num)
   (prompt "/n请选择要多排一个的单粒")
    (setq scell1 (ssget))
    (command "array" scell1 """" (fix row_num) (fix colu_num1) row_dis colu_dis "")
    (prompt "/n请选择另一个单粒")
    (setq scell2 (ssget))
    (command "array" scell2 """" (fix row_num) (fix colu_num) row_dis colu_dis "")
    )
    )
    (if(= (strcase XY) "Y")
    (progn
    (setq row_num1 (+ 0.5 row_num))
    (prompt "/n请选择要多排一个的单粒")
    (setq scell3 (ssget))
    (command "array" scell3 """" (fix row_num1) (fix colu_num) row_dis colu_dis "")
    (prompt "/n请选择另一个单粒")
    (setq scell4 (ssget))
    (command "array" scell4 """" (fix row_num) (fix colu_num) row_dis colu_dis "")
)
)
)
 )
  )

(defun is_pi_sio2()
       (setq txt_ss(ssget"x"(list(cons 0 "text"))))
       (setq sslen(sslength txt_ss))
       (if (equal sslen 2)(setq txt(ssname txt_ss 0)))
       (if txt(setq txt_apr(cdr (assoc 1 (entget txt)))))
       (if (/= (strcase(substr txt_apr 1 3)) "RFD")
       (progn (setq txt(ssname txt_ss 1))
       (if txt(setq txt_apr(cdr (assoc 1 (entget txt)))))))
       (setq txt_back txt_apr)
       (if txt_apr(setq txt_len(strlen txt_apr)))
       (while(>= txt_len 4)
             (setq is_txt(substr txt_apr 1 4))
             (if (= (strcase is_txt) (strcase"Sio2"))
                 (setq ke 0.9832
	               ce1 0.1
	               cf1 0.1
	               flag 1)	 
             )              
             (setq txt_apr(substr txt_apr 2))
             (setq txt_len(strlen txt_apr))
        )
        (while(>= txt_len 2)
             (setq is_txt(substr txt_back 1 2))
             (if (= (strcase is_txt) "T1")
                 (setq ke 0.9836
	               ce1 0.1
	               cf1 0.1
	               flag 2)
	       )
             (setq txt_back(substr txt_back 2))
             (setq txt_len(strlen txt_back))
        )
      )
  
  
  
(defun c:rfd( )
  (a_cell)
  (setq rotate (getstring "/n 请确定图形是否需要旋转 (Yes/No<N>) "))
  (if (= (strcase rotate) "Y")
  (command "rotate""all""""0,0" -90)
  )
  (setvar "osmode" 0)
  (command "zoom""e")
  (setvar "osmode" 3)
  (setq apr_ld_cn (getpoint "\n请点选凸版左下角L型的端点:"))
  (setvar "osmode" 0)
  (setq xc (+(car apr_ld_cn) 177.8 ))
  (setq yc (+(cadr apr_ld_cn)  203.2))
  (command "move" "all" "" (list xc yc) "0,0")
  (command "zoom""e")
  (command "layer""n""scl""")
  (command "zoom" "e")
  (setq ss (ssget "w" '(-177.8 -203.2) '(177.8 203.2)))
  (command "change" ss """p""la""scl""")
  (is_pi_sio2)
  (scale "scl" ke)
  (command "zoom" "e")
  (command "layer""n""ofst""")
  (prompt "/n请选择所有单粒：")
  (setq sc (ssget))
  (command "change" sc """p""la""ofst""")
  (ofst "ofst" cf1 ce1)
  (setq ss_txt (ssget "x" (list (cons 0 "TEXT"))))
  (if	(= (sslength ss_txt) 2)
      (progn
	(setq txt_dt (entget (ssname ss_txt 0)))	
	(setq apr_id (cdr (assoc 1 txt_dt)))
	(setq dateis(substr apr_id 1 3))
	(if (= (strcase dateis) "RFD")
	(setq apr_id (cdr (assoc 1 txt_dt))))
	(if(/= (strcase dateis) "RFD")
	(progn
	(setq txt_dt (entget (ssname ss_txt 1)))
	(setq apr_id (cdr (assoc 1 txt_dt)))))
	(setq c_date (getvar "CDATE"))
	(setq apr_id (strcat apr_id " QINGYI " (itoa (fix c_date))))
	(setq apr_id (strcase apr_id))
	(setq txt_dt (subst (cons 1 apr_id) (assoc 1 txt_dt) txt_dt))	
	(setq txt_dt (subst (cons 10 '(181 -79 0)) (assoc 8 txt_dt) txt_dt))
	(entmod txt_dt)
      )
    )
 (draw_edge)
  (command "change""all""""p""la""0""")
  (command "layer""lock""0""")
  (command "layer""m""0""")
  (command "clear""")
  (command "layer""unlock""0""")
  (command "zoom""e")
  (if (equal flag 1)
      (getstring (strcat "请确认系数是：Ke="
	         (rtos ke) "; Ce=" (rtos (* 2 ce1)) "; Cf=" (rtos (* 2 cf1)) " ;" "---SIO2版")
      )
  )
  (if (equal flag 2)
      (getstring (strcat "Ke="
	         (rtos ke) "; Ce=" (rtos (* 2 ce1)) "; Cf=" (rtos (* 2 cf1)) "---PI版")
  )    
  )
 )
(PROMPT"\n输入 rfd 运行程序！")
(prompt"\n请把排版数据记下来！")
(prompt"\n运行程序前请先整理层：只保留有效层即可！")
