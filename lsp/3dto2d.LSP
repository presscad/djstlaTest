(defun c:3dTO2d()
   (defun get_dt_vl (item dt)
  (cdr (assoc item dt))
	)
   (defun 3dLNTO2D()
     (setq ln_ss (ssget "x" (list (cons 0 "line"))))
     (if ln_ss
       (progn
	 (setq line_cnt (sslength ln_ss))
	 (setq cnt 0)
	 (while (< cnt line_cnt)
	   (setq ent_name (ssname ln_ss cnt))
	   (setq ln_dt (entget ent_name))
	   (setq stt_pt (get_dt_vl 10 ln_dt))
	   (setq end_pt (get_dt_vl 11 ln_dt))
	   (if ( OR (/= (caddr stt_pt) 0.0) (/= (caddr END_pt) 0.0))
	     (progn
	   	(setq stt_pt1 (list (car stt_pt) (cadr stt_pt) 0.0000))
	   	(setq end_pt1 (list (car end_pt) (cadr end_pt) 0.0000))
	   	(setq ln_dt (subst (cons 10 stt_pt1)   (cons 10 stt_pt) ln_dt))
	   	(setq ln_dt (subst (cons 11 end_pt1)   (cons 11 end_pt) ln_dt))
	   	(entmod ln_dt)
	       )
	     )
	   (setq cnt (1+ cnt))
	  )
	 )
       )
     )

   (defun 3dACTO2D()
     (setq ln_ss (ssget "x" (list (cons 0 "arc"))))
     (if ln_ss
       (progn
	 (setq line_cnt (sslength ln_ss))
	 (setq cnt 0)
	 (while (< cnt line_cnt)
	   (setq ent_name (ssname ln_ss cnt))
	   (setq ln_dt (entget ent_name))
	   (setq stt_pt (get_dt_vl 10 LN_dt))
	   (if (/= (caddr stt_pt) 0.0)
	     (progn
	        (setq stt_pt1 (list (car stt_pt) (cadr stt_pt) 0.0000))
	   	(setq ln_dt (subst (cons 10 stt_pt1)   (cons 10 stt_pt) ln_dt))
	   	(entmod ln_dt)
	       )
	     )
	   (setq cnt (1+ cnt))
	  )
	 )
       )
     )
   (defun 3dCRTO2D()
     (setq ln_ss (ssget "x" (list (cons 0 "circle"))))
     (if ln_ss
       (progn
	 (setq line_cnt (sslength ln_ss))
	 (setq cnt 0)
	 (while (< cnt line_cnt)
	   (setq ent_name (ssname ln_ss cnt))
	   (setq ln_dt (entget ent_name))
	   (setq stt_pt (get_dt_vl 10 LN_dt))
	   (if (/= (caddr stt_pt) 0.0)
	     (progn
	        (setq stt_pt1 (list (car stt_pt) (cadr stt_pt) 0.0000))
	   	(setq ln_dt (subst (cons 10 stt_pt1)   (cons 10 stt_pt) ln_dt))
	   	(entmod ln_dt)
	       )
	     )
	   (setq cnt (1+ cnt))
	  )
	 )
       )
     )
   (3dlnto2d)
   (3dacto2d)
   (3dCRTO2D)
   )
