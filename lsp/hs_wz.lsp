(defun hs_zero() 
        (command "pline" (list -0.703727 0.292243) "w" 0 0 
                         (list -0.703727 -0.439596) 
                         (list -0.422236 -0.73266) 
                         (list 0.422236 -0.73266) 
                         (list 0.703727 -0.439596) 
                         (list 0.703727 0.439596) 
                         (list 0.422236 0.73266) 
                         (list -0.422236 0.73266) 
                         (list -0.703727 0.439596) 
                         (list -0.703727 0.293064) 
                         (list -0.703727 0.292505) 
                         (list -0.422236 0.292505) 
                         (list -0.422236 0.293064) 
                         (list -0.281491 0.439596) 
                         (list 0.281491 0.439596) 
                         (list 0.422236 0.293064) 
                         (list 0.422236 -0.293064) 
                         (list 0.281491 -0.439596) 
                         (list -0.281491 -0.439596) 
                         (list -0.422236 -0.293064) 
                         (list -0.422236 0.292243) 
                         "c"
         )
  )


(defun hs_one() 
         (command "pline" (list 0.357816 -0.750001) "w" 0 0 
                         (list -0.321023 -0.750001) 
                         (list -0.321023 -0.515999) 
                         (list -0.171023 -0.515999) 
                         (list -0.171023 0.449999) 
                         (list -0.321023 0.299999) 
                         (list -0.471023 0.449999) 
                         (list -0.171023 0.749999) 
                         (list 0.207816 0.749999) 
                         (list 0.207816 -0.515999) 
                         (list 0.357816 -0.515999) 
                         "c"
         )
  )


(defun hs_two() 
        (command "pline" (list 0.466339 0.75) "w" 0 0 
                         (list 0.75 0.430148) 
                         (list 0.75 0.146487) 
                         (list 0.466339 -0.137174) 
                         (list -0.134367 -0.137174) 
                         (list -0.418027 -0.420834) 
                         (list 0.75 -0.420834) 
                         (list 0.75 -0.75) 
                         (list -0.75 -0.75) 
                         (list -0.75 -0.279004) 
                         (list -0.276197 0.146487) 
                         (list 0.324509 0.146487) 
                         (list 0.466339 0.288317) 
                         (list 0.324509 0.430148) 
                         (list -0.276197 0.430148) 
                         (list -0.418027 0.288317) 
                         (list -0.75 0.288317) 
                         (list -0.75 0.430148) 
                         (list -0.418027 0.75) 
                         "c"
         )
  )


(defun hs_three() 
        (command "pline" (list -0.452621 0.748677) "w" 0 0 
                         (list 0.456377 0.748677) 
                         (list 0.75 0.455055) 
                         (list 0.75 0.161432) 
                         (list 0.603189 0.0146207) 
                         (list 0.75 -0.132191) 
                         (list 0.75 -0.456377) 
                         (list 0.456377 -0.75) 
                         (list -0.452621 -0.75) 
                         (list -0.746244 -0.456377) 
                         (list -0.746244 -0.132191) 
                         (list -0.452621 -0.132191) 
                         (list -0.452621 -0.309566) 
                         (list -0.30581 -0.456377) 
                         (list 0.309566 -0.456377) 
                         (list 0.456377 -0.309566) 
                         (list 0.309566 -0.132191) 
                         (list -0.0121874 -0.132191) 
                         (list -0.0121874 0.161432) 
                         (list 0.309566 0.161432) 
                         (list 0.456377 0.308243) 
                         (list 0.309566 0.455055) 
                         (list -0.30581 0.455055) 
                         (list -0.452621 0.308243) 
                         (list -0.452621 0.161432) 
                         (list -0.746244 0.161432) 
                         (list -0.746244 0.455055) 
                         "c"
         )
  )



(defun hs_four() 
        (command "pline" (list -0.10423 -0.141518) "w" 0 0 
                         (list -0.455972 -0.141518) 
                         (list 0.14627 0.446538) 
                         (list 0.14627 -0.141518) 
                         (list -0.103718 -0.141518) 
                         (list -0.103718 -0.435546) 
                         (list 0.14627 -0.435546) 
                         (list 0.14627 -0.75) 
                         (list 0.440298 -0.75) 
                         (list 0.440298 -0.435546) 
                         (list 0.75 -0.435546) 
                         (list 0.75 -0.141518) 
                         (list 0.440298 -0.141518) 
                         (list 0.440298 0.75) 
                         (list 0.14627 0.75) 
                         (list -0.75 -0.141518) 
                         (list -0.75 -0.435546) 
                         (list -0.10423 -0.435546) 
                         "c"
         )
  )


(defun hs_five() 
        (command "pline" (list -0.75 -0.0719393) "w" 0 0 
                         (list 0.325068 -0.0719393) 
                         (list 0.466712 -0.285541) 
                         (list 0.325068 -0.427185) 
                         (list -0.297508 -0.427185) 
                         (list -0.439152 -0.285541) 
                         (list -0.75 -0.285541) 
                         (list -0.75 -0.427185) 
                         (list -0.439152 -0.75) 
                         (list 0.466712 -0.75) 
                         (list 0.75 -0.427185) 
                         (list 0.75 -0.0719393) 
                         (list 0.466712 0.211349) 
                         (list -0.439152 0.211349) 
                         (list -0.439152 0.422678) 
                         (list 0.75 0.422678) 
                         (list 0.75 0.75) 
                         (list -0.75 0.75) 
                         "c"
         )
  )


(defun hs_six() 
        (command "pline" (list 0.0903027 -0.426924) "w" 0 0 
                         (list -0.288135 -0.426924) 
                         (list -0.432586 -0.282473) 
                         (list -0.432586 -0.138021) 
                         (list 0.316646 -0.138021) 
                         (list 0.461098 -0.282473) 
                         (list 0.316646 -0.426924) 
                         (list 0.0906896 -0.426924) 
                         (list 0.0906896 -0.75) 
                         (list 0.461098 -0.75) 
                         (list 0.75 -0.426924) 
                         (list 0.75 -0.138021) 
                         (list 0.461098 0.150881) 
                         (list -0.432586 0.150881) 
                         (list -0.432586 0.295332) 
                         (list -0.288135 0.439783) 
                         (list 0.316646 0.439783) 
                         (list 0.461098 0.295332) 
                         (list 0.75 0.295332) 
                         (list 0.75 0.439783) 
                         (list 0.461098 0.75) 
                         (list -0.432586 0.75) 
                         (list -0.75 0.439783) 
                         (list -0.75 -0.138021) 
                         (list -0.75 -0.426924) 
                         (list -0.432586 -0.75) 
                         (list 0.0903027 -0.75) 
                         "c"
         )
  )



(defun hs_seven() 
        (command "pline" (list 0.75 0.474664) "w" 0 0 
                         (list 0.75 0.75) 
                         (list -0.75 0.75) 
                         (list -0.75 0.474664) 
                         (list 0.336996 0.474664) 
                         (list -0.75 -0.612332) 
                         (list -0.75 -0.75) 
                         (list -0.474664 -0.75) 
                         "c"
         )
  )



(defun hs_eight() 
        (command "pline" (list 0.103684 -0.451986) "w" 0 0 
                         (list -0.0347375 -0.451986) 
                         (list -0.297877 -0.451986) 
                         (list -0.446218 -0.303646) 
                         (list -0.297877 -0.155305) 
                         (list -0.0347375 -0.155305) 
                         (list 0.295484 -0.155305) 
                         (list 0.443824 -0.303646) 
                         (list 0.295484 -0.451986) 
                         (list 0.104475 -0.451986) 
                         (list 0.104475 -0.748667) 
                         (list 0.443824 -0.748667) 
                         (list 0.740505 -0.451986) 
                         (list 0.740505 -0.155305) 
                         (list 0.592165 -0.00696499) 
                         (list 0.740505 0.141375) 
                         (list 0.740505 0.438056) 
                         (list 0.443824 0.75) 
                         (list 0.121607 0.75) 
                         (list 0.121607 0.438056) 
                         (list 0.295484 0.438056) 
                         (list 0.443824 0.289716) 
                         (list 0.295484 0.141375) 
                         (list -0.0347375 0.141375) 
                         (list -0.297877 0.141375) 
                         (list -0.446218 0.289716) 
                         (list -0.297877 0.438056) 
                         (list -0.0347375 0.438056) 
                         (list 0.121166 0.438056) 
                         (list 0.121166 0.75) 
                         (list -0.0347375 0.75) 
                         (list -0.446218 0.75) 
                         (list -0.742898 0.438056) 
                         (list -0.742898 0.289716) 
                         (list -0.742898 0.141375) 
                         (list -0.594558 -0.00696499) 
                         (list -0.742898 -0.155305) 
                         (list -0.742898 -0.303646) 
                         (list -0.742898 -0.451986) 
                         (list -0.446218 -0.748667) 
                         (list -0.0347375 -0.748667) 
                         (list 0.103684 -0.748667) 
                         "c"
         )
  )



 (defun hs_nine() 
        (command "pline" (list 0.247307 0.44357) "w" 0 0 
                         (list 0.292522 0.44357) 
                         (list 0.438735 0.297357) 
                         (list 0.438735 0.151145) 
                         (list -0.292329 0.151145) 
                         (list -0.438542 0.297357) 
                         (list -0.292329 0.44357) 
                         (list 0.247227 0.44357) 
                         (list 0.247227 0.75) 
                         (list -0.438542 0.75) 
                         (list -0.75 0.44357) 
                         (list -0.75 0.297357) 
                         (list -0.75 0.151145) 
                         (list -0.438542 -0.141281) 
                         (list 0.438735 -0.141281) 
                         (list 0.438735 -0.287494) 
                         (list 0.292522 -0.433707) 
                         (list -0.292329 -0.433707) 
                         (list -0.438542 -0.287494) 
                         (list -0.75 -0.287494) 
                         (list -0.75 -0.433707) 
                         (list -0.438542 -0.75) 
                         (list 0.438735 -0.75) 
                         (list 0.75 -0.433707) 
                         (list 0.75 0.44357) 
                         (list 0.438735 0.75) 
                         (list 0.247307 0.75) 
                         "c"
         )
  )              ;                      End of function:hs_one()....



(defun set_var( / osnap_old orthomode)
       (setq osnap_old (getvar "osmode"))
       (setq orthomode_old (getvar "orthomode"))
       (setvar "osmode" 0)
       (setvar "orthomode" 0)
       (list osnap_old orthomode_old)
  )             ;                       End of function set_var();


(defun getp(ent_name num / ent_data ent_cp ent_data vertex_val count dt_top pl)
  
         ;(setq ent_data(entget(car(entsel"\n---Please select a polyline:"))))
         (setq ent_data(entget ent_name))
         (setq ent_cp ent_data)
         (setq vertex_val(cdr(assoc 90 ent_data)))
    
         (print(strcat"\n" "---There is total "(itoa vertex_val)" vertexs"))
         ;(setq num(getint"\n---Please input the number of the point to see the coordinat"))

         (setq count 0)
         (while ent_cp
	        (setq dt_top(car ent_cp))
	        (setq ent_cp(cdr ent_cp))
	        (if(equal 10 (car dt_top))
		   (setq count(+ 1 count))		   
		)
	        (if (equal count num)
		       (progn
		          (setq ent_cp nil)
			  (setq pl dt_top)
		       );progn
	        ); if     
	 );while     
 );c:getp()  


(defun apr_scale(lyr_name x_scl y_scl / ss_lwpl ss_cnt i_loop pl_dt dt scl_x scl_y center)
    ;(set_var)
    ;(command "zoom" "E")    
              
    ;(initget 7)
    ;(setq x_scl (getreal "请输入X方向收缩的系数:"))
    ;(setq y_scl (getreal "请输入Y方向收缩的系数:"))
    (initget 0)
    (setq
      ss_lwpl (ssget "x"
		     (list (cons 0 "lwpolyline") (cons 8 lyr_name))
	      )
    )
    (if	ss_lwpl
      (progn
	(setq ss_cnt (sslength ss_lwpl))
	(setq i_loop 0)
	(while (< i_loop ss_cnt)
	  (setq pl_dt (entget (ssname ss_lwpl i_loop)))
	  (setq dt nil)
	  (while pl_dt
	    (if	(/= (caar pl_dt) 10)
	      (setq dt (append dt (list (car pl_dt))))
	      (progn
		(setq scl_x (* (cadar pl_dt) x_scl))
		(setq scl_y (* (caddar pl_dt) y_scl))
		(setq
		  dt (append dt (list (cons 10 (list scl_x scl_y 0))))
		)
	      )
	    )
	    (setq pl_dt (cdr pl_dt))
	  )
	  (entmod dt)
	  (setq i_loop (1+ i_loop))
	)
      )
    )
    (setq
      ss_lwpl (ssget "x"
		     (list (cons 0 "CIRCLE") (cons 8 lyr_name))
	      )
    )
	(if	ss_lwpl
      (progn
	(setq ss_cnt (sslength ss_lwpl))
	(setq i_loop 0)
	(while (< i_loop ss_cnt)
	  (setq pl_dt (entget (ssname ss_lwpl i_loop)))
	  (setq center (cdr (assoc 10 pl_dt)))
	  (setq center (list (* x_scl (car center)) (* y_scl (cadr center))))	  
	  (setq pl_dt (subst (cons 10 center) (assoc 10 pl_dt) pl_dt))
	  (entmod pl_dt)
	  (setq i_loop (1+ i_loop))
	)
      )
    )


    
    ;(command "zoom" "E")
  )         ;            End of apr_scale();                



(defun makelayer(lyname / )
  ;(setq layername "hs_wz_wz_wz")
  (command "layer" "m" lyname "s" lyname "")
  )        ;  create a new layer and set it currently


(defun draw_unit_txt(txtnum / )
       (if(equal txtnum 0)(hs_zero))
       (if(equal txtnum 1)(hs_one))
       (if(equal txtnum 2)(hs_two))
       (if(equal txtnum 3)(hs_three))
       (if(equal txtnum 4)(hs_four))
       (if(equal txtnum 5)(hs_five))
       (if(equal txtnum 6)(hs_six))
       (if(equal txtnum 7)(hs_seven))
       (if(equal txtnum 8)(hs_eight))
       (if(equal txtnum 9)(hs_nine))
  )


(defun ajust_wz(  wz_num      base_point    rota_mirr     xscale       yscale     lyrname /
		  x_scale     y_scale       ss_txt        hundred_num  ten_num    one_num
		  ent_last
	       )

       (set_var)
       (setq x_scale xscale y_scale yscale)
       ;(setq layername "hs_wz_wz_wz")
       ;(makelayer layername)  
       (setq ss_txt(ssadd));  Creat a pickset for future using!
  
       (setq hundred_num(/ wz_num 100))
       (setq ten_num(/ (- wz_num (* 100 hundred_num)) 10))
       (setq one_num(- wz_num (* 100 hundred_num) (* 10 ten_num)))
  
       (if(not(equal hundred_num 0))
	   (progn
	       (draw_unit_txt hundred_num)
	       (setq ent_last(entlast))
	       (command "move" ent_last "" "0,0" "-1.5,0")
	       (setq ss_txt(ssadd ent_last ss_txt))

	       (draw_unit_txt ten_num)
	       (setq ent_last(entlast))	   
	       (setq ss_txt(ssadd ent_last ss_txt))

	       (draw_unit_txt one_num)
	       (setq ent_last(entlast))
	       (command "move" ent_last "" "0,0" "1.5,0")
	       (setq ss_txt(ssadd ent_last ss_txt))
	     )
	 )
  
       (if (and(equal hundred_num 0)(not(equal ten_num 0)))
	   (progn
	        (draw_unit_txt ten_num)
	        (setq ent_last(entlast))	   
	        (command "move" ent_last "" "0,0" "-0.75,0")
	        (if(equal hundred_num 0)())
	        (setq ss_txt(ssadd ent_last ss_txt))

	        (draw_unit_txt one_num)
	        (setq ent_last(entlast))	   
	        (command "move" ent_last "" "0,0" "0.75,0")	        
	        (setq ss_txt(ssadd ent_last ss_txt))
	     )	    
	 )

        (if(and(equal hundred_num 0)(equal ten_num 0))
	      (progn
		   (draw_unit_txt one_num)
		   (setq ent_last(entlast))
		   (setq ss_txt(ssadd ent_last ss_txt))
		)
	  )
  
        (if(and (>= wz_num 10)(<= wz_num 99))
	   (progn
	   	(setq x_scale (* 0.5 x_scale))
           	(setq y_scale (* 1.0 y_scale))
	     )
	  )
        (if(and (>= wz_num 100)(<= wz_num 999))
	   (progn
	   	(setq x_scale (* (/ 1.0 3.0) x_scale))
           	(setq y_scale (* 0.92 y_scale))
	     )
	  )
        (apr_scale lyrname x_scale y_scale) ; Scale the wz
  
        (cond ((equal rota_mirr "1")(command "rotate" ss_txt "" "0,0" "90" ))
	      ((equal rota_mirr "2")(command "rotate" ss_txt "" "0,0" "180" ))
	      ((equal rota_mirr "3")(command "rotate" ss_txt "" "0,0" "270" ))
	  )
        (if   (equal rota_mirr "4")
	      (progn
	          (command "rotate" ss_txt "" "0,0" "90" )
	      	  (command "mirror" ss_txt "" "0,0" "0,12.5" "y")
	      )
	  )
        (if   (equal rota_mirr "5")
	      (progn
	      	  (command "rotate" ss_txt "" "0,0" "90" )
	      	  (command "mirror" ss_txt "" "0,0" "12.5,0" "y")
	      )
	  )
       (if   (equal rota_mirr "6")	 
	     (command "mirror" ss_txt "" "0,0" "0,12.5" "y")
	  )
       
       (if   (equal rota_mirr "7")
	     (command "mirror" ss_txt "" "0,0" "12.5,0""y")
	  )
       (command "change" ss_txt "" "p" "la" "ok" "")
       (command "move" ss_txt "" "0,0" base_point)
       
        
  )

(defun c:hswz( / rota      box_basep   box_ent    p1         p2          p3         p4      x_min      y_min
	          x_max     y_max       dist_x     dist_y     box_center  scl_x      scl_y   x_arrays   x_step
	          y_arrays  y_step      layername  cal_x      cal_y       txt_number txt_center
	      )
  
      (print"\n 请输入文字书写方式:" )
      (setq rota(getstring"\n正字0度<0> /正字90度<1> /正字180度<2> /正字270度<3>
                            \n90度左右镜相<4> /90度上下镜相<5>  /正字左右镜相<6> /正字上下镜相<7> /Enter:"))  
      (setq box_basep(getpoint"\n请选中文字排版框的左下角的顶点:"))
      (setq box_ent(ssname (ssget box_basep) 0))
      
      (setq p1(cdr(getp box_ent 1)))
      (setq p2(cdr(getp box_ent 2)))
      (setq p3(cdr(getp box_ent 3)))
      (setq p4(cdr(getp box_ent 4)))

      (setq x_min (car p1) x_max (car p1))
      (setq y_min (cadr p1) y_max(cadr p1))
      (if(< (car p2) x_min)(setq x_min (car p2)))   ;2	
      (if(> (car p2) x_max)(setq x_max (car p2)))   ;2
      (if(< (cadr p2) y_min)(setq y_min (cadr p2))) ;2
      (if(> (cadr p2) y_max)(setq y_max (cadr p2))) ;2
  
      (if(< (car p3) x_min)(setq x_min (car p3)))   ; 3	
      (if(> (car p3) x_max)(setq x_max (car p3)))   ; 3
      (if(< (cadr p3) y_min)(setq y_min (cadr p3))) ; 3
      (if(> (cadr p3) y_max)(setq y_max (cadr p3))) ; 3
  
      (if(< (car p4) x_min)(setq x_min (car p4)))   ;  4	
      (if(> (car p4) x_max)(setq x_max (car p4)))   ;  4
      (if(< (cadr p4) y_min)(setq y_min (cadr p4))) ;  4
      (if(> (cadr p4) y_max)(setq y_max (cadr p4))) ;  4

      (setq dist_x(- x_max x_min))
      (setq dist_y(- y_max y_min))
      (setq box_center(list(+ (car box_basep) (/ dist_x 2))
					 (+ (cadr box_basep)(/ dist_y 2)))) ;条件  四   


      (setq scl_x(/ dist_x 1.55));-----
      (setq scl_y(/ dist_y 1.55))
      (if(or(equal rota "1")(equal rota "3")(equal rota "4")(equal rota "5"))
         (progn
	     (setq scl_x(/ dist_y 1.5))
	     (setq scl_y(/ dist_x 1.5))
	  )
	) ;                 
                              
      (setq x_arrays(getint"\n请输入x方向的排版个数:"))
      (setq x_step(getreal"\n请输入x方向的排版步距:"))
      (setq y_arrays(getint"\n请输入y方向的排版个数:"))
      (setq y_step(getreal"\n请输入y方向的排版步距:"))  ;排版

      (setq layername "ok")
      (makelayer layername)
  
      (setq layername "w_s")
      (makelayer layername)        
      (setq cal_x 0 cal_y 0 txt_number 1)
      (while (< cal_y  y_arrays)
	     (while (< cal_x  x_arrays)	            
	            (setq txt_center(list(+ (car box_center) (* cal_x x_step))
					 (+ (cadr box_center) (* cal_y y_step))))            
	            (ajust_wz txt_number txt_center rota scl_x scl_y layername) 
	       
	            (setq cal_x (+ 1 cal_x))
	            (setq txt_number (+ 1 txt_number))
	       )
	     (setq cal_x 0)
	     (setq cal_y (+ 1 cal_y))	    
	)      
 )

(getstring"\n-----请输入 hswz  执行命令-----")
(getstring"\n-----注意：框要闭合------------")
