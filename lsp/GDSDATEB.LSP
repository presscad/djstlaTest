(defun c:gd () 
        (command "pline" (list -107.848 -175.327) "w" 0 0 
                         (list -108.21 -175.327) 
                         (list -108.969 -175.327) 
                         (list -108.969 -174.744) 
                         (list -108.21 -174.744) 
                         (list -108.191 -174.476) 
                         (list -108.959 -174.476) 
                         (list -108.959 -173.995) 
                         (list -108.191 -173.995) 
                         (list -108.182 -173.708) 
                         (list -108.969 -173.708) 
                         (list -108.969 -173.209) 
                         (list -109.293 -173.218) 
                         (list -109.293 -175.345) 
                         (list -109.904 -175.345) 
                         (list -109.904 -173.218) 
                         (list -109.293 -173.218) 
                         (list -108.969 -173.209) 
                         (list -108.182 -173.209) 
                         (list -108.182 -173.708) 
                         (list -108.191 -173.995) 
                         (list -108.191 -174.476) 
                         (list -108.21 -174.744) 
                         (list -108.21 -175.327) 
                         (list -107.848 -175.327) 
                         (list -107.848 -173.209) 
                         (list -107.247 -173.209) 
                         (list -107.247 -175.327) 
                         (list -107.256 -175.604) 
                         (list -107.237 -175.873) 
                         (list -106.886 -175.863) 
                         (list -106.876 -172.931) 
                         (list -108.487 -172.94) 
                         (list -108.348 -172.311) 
                         (list -106.515 -172.321) 
                         (list -106.525 -172.006) 
                         (list -110.626 -171.997) 
                         (list -110.617 -172.006) 
                         (list -110.626 -172.321) 
                         (list -108.746 -172.311) 
                         (list -108.867 -172.931) 
                         (list -110.274 -172.931) 
                         (list -110.274 -175.873) 
                         (list -109.922 -175.882) 
                         (list -109.913 -175.614) 
                         (list -107.256 -175.604) 
                         (list -107.247 -175.327) 
                         "c"
         )
        (command "pline" (list -114.692 -173.361) "w" 0 0 
                         (list -114.185 -173.357) 
                         (list -114.185 -174.134) 
                         (list -114.689 -174.132) 
                         (list -114.685 -174.41) 
                         (list -114.194 -174.393) 
                         (list -114.185 -175.336) 
                         (list -114.296 -175.401) 
                         (list -114.583 -175.392) 
                         (list -114.481 -175.789) 
                         (list -114.344 -175.765) 
                         (list -114.208 -175.737) 
                         (list -114.073 -175.706) 
                         (list -114.065 -175.704) 
                         (list -114.057 -175.702) 
                         (list -114.049 -175.699) 
                         (list -114.041 -175.696) 
                         (list -114.034 -175.693) 
                         (list -114.026 -175.689) 
                         (list -114.019 -175.685) 
                         (list -114.011 -175.681) 
                         (list -114.004 -175.677) 
                         (list -113.997 -175.673) 
                         (list -113.99 -175.668) 
                         (list -113.983 -175.663) 
                         (list -113.977 -175.658) 
                         (list -113.97 -175.652) 
                         (list -113.964 -175.647) 
                         (list -113.958 -175.641) 
                         (list -113.952 -175.635) 
                         (list -113.947 -175.628) 
                         (list -113.942 -175.622) 
                         (list -113.936 -175.615) 
                         (list -113.932 -175.609) 
                         (list -113.927 -175.602) 
                         (list -113.922 -175.594) 
                         (list -113.918 -175.587) 
                         (list -113.914 -175.58) 
                         (list -113.911 -175.572) 
                         (list -113.907 -175.565) 
                         (list -113.904 -175.557) 
                         (list -113.901 -175.549) 
                         (list -113.899 -175.541) 
                         (list -113.896 -175.533) 
                         (list -113.894 -175.525) 
                         (list -113.893 -175.517) 
                         (list -113.891 -175.508) 
                         (list -113.89 -175.5) 
                         (list -113.889 -175.492) 
                         (list -113.889 -175.483) 
                         (list -113.888 -175.475) 
                         (list -113.87 -172.034) 
                         (list -115.008 -172.025) 
                         (list -114.99 -174.254) 
                         (list -114.991 -174.34) 
                         (list -114.994 -174.427) 
                         (list -115.001 -174.513) 
                         (list -115.01 -174.599) 
                         (list -115.023 -174.685) 
                         (list -115.038 -174.77) 
                         (list -115.056 -174.855) 
                         (list -115.077 -174.939) 
                         (list -115.101 -175.022) 
                         (list -115.127 -175.105) 
                         (list -115.156 -175.186) 
                         (list -115.188 -175.267) 
                         (list -115.223 -175.346) 
                         (list -115.261 -175.424) 
                         (list -115.3 -175.501) 
                         (list -115.343 -175.577) 
                         (list -115.388 -175.651) 
                         (list -115.055 -175.799) 
                         (list -115.006 -175.704) 
                         (list -114.961 -175.607) 
                         (list -114.919 -175.509) 
                         (list -114.88 -175.41) 
                         (list -114.845 -175.309) 
                         (list -114.813 -175.207) 
                         (list -114.785 -175.104) 
                         (list -114.76 -175.0) 
                         (list -114.739 -174.896) 
                         (list -114.721 -174.79) 
                         (list -114.708 -174.694) 
                         (list -114.698 -174.597) 
                         (list -114.69 -174.499) 
                         (list -114.684 -174.402) 
                         (list -114.703 -172.302) 
                         (list -114.185 -172.302) 
                         (list -114.185 -173.079) 
                         (list -114.699 -173.076) 
                         "c"
         )
        (command "pline" (list -111.731 -173.172) "w" 0 0 
                         (list -111.731 -173.495) 
                         (list -111.74 -173.754) 
                         (list -111.74 -174.05) 
                         (list -113.185 -174.05) 
                         (list -113.185 -173.754) 
                         (list -111.74 -173.754) 
                         (list -111.731 -173.495) 
                         (list -113.185 -173.495) 
                         (list -113.185 -173.172) 
                         (list -111.731 -173.172) 
                         (list -112.191 -172.913) 
                         (list -112.71 -172.913) 
                         (list -112.71 -172.503) 
                         (list -112.191 -172.503) 
                         (list -112.185 -172.265) 
                         (list -112.722 -172.256) 
                         (list -112.713 -171.784) 
                         (list -113.018 -171.793) 
                         (list -113.027 -171.784) 
                         (list -113.018 -172.237) 
                         (list -113.657 -172.228) 
                         (list -113.638 -172.515) 
                         (list -113.009 -172.496) 
                         (list -113.018 -172.922) 
                         (list -113.499 -172.931) 
                         (list -113.49 -174.309) 
                         (list -112.648 -174.309) 
                         (list -112.685 -174.689) 
                         (list -113.685 -174.689) 
                         (list -113.685 -174.975) 
                         (list -112.768 -174.966) 
                         (list -112.783 -175.001) 
                         (list -112.8 -175.035) 
                         (list -112.817 -175.069) 
                         (list -112.836 -175.102) 
                         (list -112.855 -175.134) 
                         (list -112.876 -175.166) 
                         (list -112.898 -175.197) 
                         (list -112.921 -175.227) 
                         (list -112.945 -175.257) 
                         (list -112.97 -175.285) 
                         (list -112.996 -175.313) 
                         (list -113.023 -175.34) 
                         (list -113.05 -175.366) 
                         (list -113.079 -175.391) 
                         (list -113.108 -175.415) 
                         (list -113.138 -175.438) 
                         (list -113.182 -175.469) 
                         (list -113.226 -175.498) 
                         (list -113.272 -175.526) 
                         (list -113.318 -175.552) 
                         (list -113.365 -175.577) 
                         (list -113.414 -175.6) 
                         (list -113.462 -175.622) 
                         (list -113.512 -175.642) 
                         (list -113.562 -175.66) 
                         (list -113.613 -175.676) 
                         (list -113.664 -175.691) 
                         (list -113.716 -175.704) 
                         (list -113.768 -175.715) 
                         (list -113.736 -175.737) 
                         (list -113.705 -175.759) 
                         (list -113.674 -175.782) 
                         (list -113.645 -175.807) 
                         (list -113.616 -175.832) 
                         (list -113.588 -175.858) 
                         (list -113.561 -175.885) 
                         (list -113.535 -175.913) 
                         (list -113.51 -175.942) 
                         (list -113.486 -175.972) 
                         (list -113.462 -176.002) 
                         (list -113.288 -175.892) 
                         (list -113.117 -175.777) 
                         (list -112.95 -175.656) 
                         (list -112.787 -175.53) 
                         (list -112.768 -175.515) 
                         (list -112.75 -175.499) 
                         (list -112.732 -175.482) 
                         (list -112.715 -175.465) 
                         (list -112.699 -175.447) 
                         (list -112.683 -175.429) 
                         (list -112.668 -175.41) 
                         (list -112.653 -175.391) 
                         (list -112.639 -175.371) 
                         (list -112.626 -175.35) 
                         (list -112.613 -175.33) 
                         (list -112.601 -175.308) 
                         (list -112.511 -175.134) 
                         (list -112.426 -174.957) 
                         (list -112.37 -174.966) 
                         (list -112.334 -175.042) 
                         (list -112.295 -175.117) 
                         (list -112.253 -175.19) 
                         (list -112.209 -175.262) 
                         (list -112.163 -175.332) 
                         (list -112.114 -175.4) 
                         (list -112.063 -175.467) 
                         (list -112.009 -175.532) 
                         (list -111.953 -175.595) 
                         (list -111.92 -175.63) 
                         (list -111.886 -175.664) 
                         (list -111.85 -175.697) 
                         (list -111.814 -175.728) 
                         (list -111.776 -175.759) 
                         (list -111.737 -175.787) 
                         (list -111.698 -175.815) 
                         (list -111.657 -175.841) 
                         (list -111.616 -175.866) 
                         (list -111.574 -175.889) 
                         (list -111.53 -175.911) 
                         (list -111.487 -175.932) 
                         (list -111.442 -175.951) 
                         (list -111.397 -175.968) 
                         (list -111.352 -175.984) 
                         (list -111.32 -175.932) 
                         (list -111.286 -175.882) 
                         (list -111.25 -175.833) 
                         (list -111.213 -175.786) 
                         (list -111.175 -175.739) 
                         (list -111.134 -175.694) 
                         (list -111.092 -175.651) 
                         (list -111.153 -175.63) 
                         (list -111.213 -175.608) 
                         (list -111.272 -175.584) 
                         (list -111.33 -175.558) 
                         (list -111.388 -175.53) 
                         (list -111.444 -175.5) 
                         (list -111.5 -175.468) 
                         (list -111.554 -175.434) 
                         (list -111.607 -175.399) 
                         (list -111.659 -175.362) 
                         (list -111.71 -175.323) 
                         (list -111.759 -175.283) 
                         (list -111.808 -175.241) 
                         (list -111.854 -175.197) 
                         (list -111.899 -175.152) 
                         (list -111.943 -175.105) 
                         (list -111.985 -175.057) 
                         (list -112.026 -175.008) 
                         (list -112.064 -174.957) 
                         (list -111.213 -174.966) 
                         (list -111.213 -174.689) 
                         (list -112.361 -174.698) 
                         (list -112.333 -174.309) 
                         (list -111.426 -174.3) 
                         (list -111.426 -172.931) 
                         (list -111.907 -172.922) 
                         (list -111.907 -172.496) 
                         (list -111.231 -172.515) 
                         (list -111.25 -172.237) 
                         (list -111.898 -172.256) 
                         (list -111.879 -171.803) 
                         (list -112.213 -171.793) 
                         (list -112.185 -172.265) 
                         (list -112.191 -172.503) 
                         (list -112.191 -172.913) 
                         "c"
         )
        (command "pline" (list -80.5197 -175.543) "w" 0 0 
                         (list -80.4889 -175.481) 
                         (list -80.5135 -175.401) 
                         (list -80.6739 -175.376) 
                         (list -80.717 -175.302) 
                         (list -80.717 -175.161) 
                         (list -80.7355 -175.05) 
                         (list -80.7602 -174.908) 
                         (list -80.7972 -174.791) 
                         (list -80.8897 -174.686) 
                         (list -80.9884 -174.618) 
                         (list -81.1487 -174.532) 
                         (list -81.3091 -174.495) 
                         (list -81.3831 -174.47) 
                         (list -81.5496 -174.458) 
                         (list -81.6606 -174.439) 
                         (list -81.6791 -174.433) 
                         (list -81.5804 -174.421) 
                         (list -81.4448 -174.409) 
                         (list -81.2536 -174.384) 
                         (list -81.0932 -174.347) 
                         (list -80.9082 -174.285) 
                         (list -80.7479 -174.18) 
                         (list -80.6739 -174.082) 
                         (list -80.5999 -173.897) 
                         (list -80.6307 -173.767) 
                         (list -80.7232 -173.663) 
                         (list -80.8404 -173.589) 
                         (list -80.8484 -173.585) 
                         (list -81.5582 -173.935) 
                         (list -81.5545 -174.15) 
                         (list -81.5792 -174.224) 
                         (list -81.6039 -174.254) 
                         (list -81.6717 -174.316) 
                         (list -81.7334 -174.328) 
                         (list -81.8012 -174.341) 
                         (list -81.9677 -174.347) 
                         (list -82.3686 -174.335) 
                         (list -82.4056 -174.304) 
                         (list -82.3933 -173.583) 
                         (list -82.3686 -173.564) 
                         (list -81.8136 -173.564) 
                         (list -81.7087 -173.576) 
                         (list -81.6471 -173.613) 
                         (list -81.6162 -173.656) 
                         (list -81.5977 -173.712) 
                         (list -81.5792 -173.749) 
                         (list -81.5607 -173.786) 
                         (list -81.5582 -173.935) 
                         (list -80.8484 -173.585) 
                         (list -81.0254 -173.515) 
                         (list -81.0809 -173.496) 
                         (list -81.3893 -173.459) 
                         (list -81.5311 -173.459) 
                         (list -81.784 -173.435) 
                         (list -82.2342 -173.422) 
                         (list -83.554 -173.435) 
                         (list -83.6033 -173.441) 
                         (list -83.6095 -173.552) 
                         (list -83.554 -173.564) 
                         (list -83.2456 -173.57) 
                         (list -83.2271 -175.401) 
                         (list -83.5355 -175.395) 
                         (list -83.5293 -175.093) 
                         (list -83.5293 -175.013) 
                         (list -83.5046 -175.0) 
                         (list -83.517 -174.828) 
                         (list -83.5601 -174.815) 
                         (list -83.6835 -174.809) 
                         (list -83.7451 -174.963) 
                         (list -83.8191 -175.099) 
                         (list -83.9425 -175.222) 
                         (list -84.035 -175.302) 
                         (list -84.1152 -175.333) 
                         (list -84.257 -175.364) 
                         (list -84.3989 -175.413) 
                         (list -84.6764 -175.413) 
                         (list -85.1809 -175.407) 
                         (list -85.2117 -175.37) 
                         (list -85.2179 -174.513) 
                         (list -85.0884 -174.544) 
                         (list -84.9465 -174.569) 
                         (list -84.7862 -174.6) 
                         (list -84.6443 -174.649) 
                         (list -84.595 -174.723) 
                         (list -84.558 -174.797) 
                         (list -84.5518 -174.92) 
                         (list -84.521 -174.939) 
                         (list -84.3606 -174.945) 
                         (list -84.3483 -174.92) 
                         (list -84.3545 -174.014) 
                         (list -84.3853 -174.002) 
                         (list -84.5333 -174.008) 
                         (list -84.5641 -174.026) 
                         (list -84.5765 -174.106) 
                         (list -84.5888 -174.168) 
                         (list -84.6135 -174.236) 
                         (list -84.6751 -174.273) 
                         (list -84.743 -174.328) 
                         (list -84.7738 -174.353) 
                         (list -84.9033 -174.365) 
                         (list -84.9897 -174.372) 
                         (list -85.2117 -174.372) 
                         (list -85.2117 -173.564) 
                         (list -84.9095 -173.558) 
                         (list -84.743 -173.57) 
                         (list -84.4963 -173.57) 
                         (list -84.373 -173.595) 
                         (list -84.2619 -173.62) 
                         (list -84.1756 -173.656) 
                         (list -84.0954 -173.724) 
                         (list -84.0029 -173.829) 
                         (list -83.9413 -173.891) 
                         (list -83.8796 -173.971) 
                         (list -83.8241 -174.008) 
                         (list -83.7439 -174.02) 
                         (list -83.6637 -174.008) 
                         (list -83.6637 -173.909) 
                         (list -83.6637 -173.435) 
                         (list -86.3835 -173.441) 
                         (list -86.3958 -173.472) 
                         (list -86.3896 -173.546) 
                         (list -86.365 -173.583) 
                         (list -86.0566 -173.583) 
                         (list -86.0566 -175.395) 
                         (list -86.4266 -175.407) 
                         (list -86.439 -175.45) 
                         (list -86.4451 -175.524) 
                         (list -86.3958 -175.537) 
                         (list -81.9616 -175.524) 
                         (list -81.9431 -175.5) 
                         (list -81.9492 -175.413) 
                         (list -81.9677 -175.395) 
                         (list -82.3686 -175.389) 
                         (list -82.3871 -174.495) 
                         (list -82.3686 -174.476) 
                         (list -82.1466 -174.489) 
                         (list -82.0233 -174.501) 
                         (list -81.9307 -174.532) 
                         (list -81.8321 -174.581) 
                         (list -81.7766 -174.63) 
                         (list -81.7211 -174.729) 
                         (list -81.6902 -174.785) 
                         (list -81.6779 -174.883) 
                         (list -81.6594 -175.025) 
                         (list -81.6532 -175.142) 
                         (list -81.61 -175.296) 
                         (list -81.5422 -175.364) 
                         (list -81.4435 -175.444) 
                         (list -81.3017 -175.506) 
                         (list -81.1352 -175.549) 
                         (list -81.0427 -175.567) 
                         (list -80.5246 -175.555) 
                         "c"
         )
        (command "pline" (list -89.0803 -173.453) "w" 0 0 
                         (list -89.0741 -173.576) 
                         (list -88.9446 -173.583) 
                         (list -88.8767 -173.595) 
                         (list -88.8706 -175.401) 
                         (list -88.8891 -175.426) 
                         (list -89.2468 -175.426) 
                         (list -89.2591 -175.45) 
                         (list -89.2591 -175.53) 
                         (list -89.2283 -175.549) 
                         (list -89.1851 -175.561) 
                         (list -87.6001 -175.555) 
                         (list -87.5631 -175.53) 
                         (list -87.557 -175.444) 
                         (list -87.594 -175.407) 
                         (list -88.0195 -175.401) 
                         (list -88.0257 -174.692) 
                         (list -88.0133 -174.624) 
                         (list -87.9948 -174.6) 
                         (list -87.9332 -174.6) 
                         (list -87.853 -174.593) 
                         (list -87.7851 -174.593) 
                         (list -87.52 -174.587) 
                         (list -87.3103 -174.581) 
                         (list -87.0821 -174.587) 
                         (list -86.9464 -174.556) 
                         (list -86.7306 -174.519) 
                         (list -86.564 -174.458) 
                         (list -86.3975 -174.359) 
                         (list -86.2989 -174.261) 
                         (list -86.231 -174.15) 
                         (list -86.2248 -174.076) 
                         (list -86.2125 -173.971) 
                         (list -86.2495 -173.86) 
                         (list -86.2927 -173.767) 
                         (list -86.3605 -173.681) 
                         (list -86.5024 -173.607) 
                         (list -86.6257 -173.546) 
                         (list -86.7737 -173.515) 
                         (list -86.9341 -173.496) 
                         (list -87.0098 -173.491) 
                         (list -88.038 -173.589) 
                         (list -87.7666 -173.583) 
                         (list -87.6125 -173.57) 
                         (list -87.4213 -173.583) 
                         (list -87.2794 -173.632) 
                         (list -87.2116 -173.712) 
                         (list -87.1684 -173.811) 
                         (list -87.1499 -173.922) 
                         (list -87.1561 -174.057) 
                         (list -87.1438 -174.168) 
                         (list -87.1684 -174.267) 
                         (list -87.1684 -174.291) 
                         (list -87.2363 -174.409) 
                         (list -87.3103 -174.446) 
                         (list -87.3596 -174.458) 
                         (list -87.5076 -174.458) 
                         (list -88.0195 -174.458) 
                         (list -88.0195 -174.439) 
                         (list -88.038 -173.589) 
                         (list -87.0098 -173.491) 
                         (list -87.1253 -173.484) 
                         (list -87.2979 -173.459) 
                         (list -87.5015 -173.453) 
                         (list -87.7173 -173.441) 
                         "c"
         )
        (command "pline" (list -78.2625 -175.382) "w" 0 0 
                         (list -78.3118 -175.395) 
                         (list -78.3057 -175.493) 
                         (list -78.244 -175.506) 
                         (list -76.6775 -175.506) 
                         (list -76.6344 -175.481) 
                         (list -76.6344 -175.382) 
                         (list -76.7145 -175.37) 
                         (list -77.0661 -175.37) 
                         (list -77.0846 -173.546) 
                         (list -76.7207 -173.552) 
                         (list -76.659 -173.515) 
                         (list -76.6529 -173.435) 
                         (list -76.6775 -173.41) 
                         (list -76.733 -173.398) 
                         (list -78.0035 -173.404) 
                         (list -78.5647 -174.544) 
                         (list -78.5894 -174.563) 
                         (list -79.1691 -173.41) 
                         (list -80.5567 -173.416) 
                         (list -80.569 -173.533) 
                         (list -80.5135 -173.558) 
                         (list -80.1435 -173.558) 
                         (list -80.1373 -175.259) 
                         (list -80.1497 -175.315) 
                         (list -80.1805 -175.376) 
                         (list -80.273 -175.389) 
                         (list -80.3655 -175.407) 
                         (list -80.3655 -175.481) 
                         (list -80.3532 -175.506) 
                         (list -79.5206 -175.518) 
                         (list -79.4898 -175.493) 
                         (list -79.4898 -175.426) 
                         (list -79.5144 -175.389) 
                         (list -79.8598 -175.382) 
                         (list -79.8968 -175.327) 
                         (list -79.9215 -175.265) 
                         (list -79.94 -173.65) 
                         (list -79.9215 -173.656) 
                         (list -79.0642 -175.45) 
                         (list -79.0149 -175.506) 
                         (list -78.8237 -175.5) 
                         (list -77.948 -173.681) 
                         (list -77.9171 -173.632) 
                         (list -77.8925 -173.7) 
                         (list -77.8863 -175.352) 
                         (list -77.8925 -175.376) 
                         (list -78.2193 -175.382) 
                         "c"
         )
        (command "pline" (list -95.2507 -172.808) "w" 0 0 
                         (list -95.2195 -172.832) 
                         (list -95.1104 -172.793) 
                         (list -92.9594 -171.889) 
                         (list -93.0607 -171.866) 
                         (list -93.1698 -171.866) 
                         (list -94.9 -172.59) 
                         (list -94.9078 -172.645) 
                         (list -95.2663 -172.793) 
                         "c"
         )
        (command "pline" (list -95.656 -173.276) "w" 0 0 
                         (list -95.5936 -173.284) 
                         (list -92.445 -171.944) 
                         (list -92.5853 -171.905) 
                         (list -92.7646 -171.913) 
                         (list -93.0997 -172.068) 
                         (list -93.0763 -172.1) 
                         (list -94.8376 -172.832) 
                         (list -94.8454 -172.894) 
                         (list -95.656 -173.245) 
                         "c"
         )
        (command "pline" (list -95.9054 -173.665) "w" 0 0 
                         (list -95.7729 -173.634) 
                         (list -92.0242 -172.037) 
                         (list -92.1489 -171.998) 
                         (list -92.297 -171.983) 
                         (list -92.3359 -171.99) 
                         (list -93.0373 -172.302) 
                         (list -93.0841 -172.411) 
                         (list -94.8454 -173.136) 
                         (list -95.0247 -173.245) 
                         (list -95.882 -173.611) 
                         (list -95.921 -173.65) 
                         "c"
         )
        (command "pline" (list -96.0612 -174.016) "w" 0 0 
                         (list -95.9599 -174.016) 
                         (list -95.843 -173.985) 
                         (list -91.7124 -172.17) 
                         (list -91.8371 -172.131) 
                         (list -91.954 -172.131) 
                         (list -93.0607 -172.606) 
                         (list -93.0607 -172.668) 
                         (list -94.8376 -173.408) 
                         (list -94.8688 -173.447) 
                         (list -94.9623 -173.502) 
                         (list -96.0846 -173.992) 
                         "c"
         )
        (command "pline" (list -96.1314 -174.351) "w" 0 0 
                         (list -91.4319 -172.349) 
                         (list -91.502 -172.279) 
                         (list -91.6189 -172.271) 
                         (list -91.6813 -172.286) 
                         (list -92.9516 -172.855) 
                         (list -93.014 -172.894) 
                         (list -93.0451 -172.964) 
                         (list -94.7987 -173.689) 
                         (list -94.8221 -173.735) 
                         (list -96.1626 -174.304) 
                         "c"
         )
        (command "pline" (list -96.2093 -174.655) "w" 0 0 
                         (list -96.108 -174.662) 
                         (list -91.1903 -172.52) 
                         (list -91.2682 -172.466) 
                         (list -91.3929 -172.458) 
                         (list -93.0373 -173.159) 
                         (list -92.9984 -173.221) 
                         (list -94.7987 -173.953) 
                         (list -94.8376 -174.0) 
                         (list -94.9312 -174.055) 
                         (list -96.2015 -174.608) 
                         "c"
         )
        (command "pline" (list -96.1859 -174.943) "w" 0 0 
                         (list -90.9331 -172.723) 
                         (list -91.0188 -172.645) 
                         (list -91.1045 -172.606) 
                         (list -93.0451 -173.447) 
                         (list -92.9906 -173.486) 
                         (list -94.7363 -174.234) 
                         (list -94.8299 -174.304) 
                         (list -96.2249 -174.912) 
                         "c"
         )
        (command "pline" (list -95.7885 -176.659) "w" 0 0 
                         (list -95.7183 -176.605) 
                         (list -93.5205 -175.67) 
                         (list -93.4972 -175.701) 
                         (list -93.5283 -175.74) 
                         (list -93.7933 -175.849) 
                         (list -93.9336 -175.911) 
                         (list -93.9414 -175.974) 
                         (list -94.4714 -176.184) 
                         (list -94.5259 -176.176) 
                         (list -94.5181 -176.215) 
                         (list -94.4558 -176.238) 
                         (list -94.6272 -176.254) 
                         (list -95.6014 -176.667) 
                         "c"
         )
        (command "pline" (list -96.3886 -176.612) "w" 0 0 
                         (list -93.2478 -175.272) 
                         (list -93.2244 -175.249) 
                         (list -93.1465 -175.234) 
                         (list -93.1542 -175.28) 
                         (list -93.1776 -175.327) 
                         (list -93.9336 -175.639) 
                         (list -93.957 -175.724) 
                         (list -95.1494 -176.215) 
                         (list -95.1728 -176.223) 
                         (list -95.1104 -176.254) 
                         (list -95.2975 -176.254) 
                         (list -95.6482 -176.394) 
                         (list -95.7105 -176.402) 
                         (list -95.7339 -176.457) 
                         (list -95.7417 -176.511) 
                         (list -96.069 -176.651) 
                         (list -96.2171 -176.651) 
                         "c"
         )
        (command "pline" (list -96.7471 -176.488) "w" 0 0 
                         (list -92.9282 -174.875) 
                         (list -92.9126 -174.906) 
                         (list -92.8971 -174.937) 
                         (list -93.9882 -175.382) 
                         (list -94.0037 -175.413) 
                         (list -95.1806 -175.911) 
                         (list -95.7651 -176.153) 
                         (list -95.7729 -176.184) 
                         (list -95.7729 -176.223) 
                         (list -95.7495 -176.254) 
                         (list -95.9054 -176.27) 
                         (list -96.4977 -176.55) 
                         (list -96.6068 -176.573) 
                         (list -96.6535 -176.558) 
                         "c"
         )
        (command "pline" (list -97.0978 -176.347) "w" 0 0 
                         (list -92.7879 -174.517) 
                         (list -92.7646 -174.525) 
                         (list -92.7412 -174.548) 
                         (list -92.7568 -174.587) 
                         (list -93.9648 -175.086) 
                         (list -93.9804 -175.117) 
                         (list -95.7573 -175.864) 
                         (list -95.7495 -175.911) 
                         (list -96.3028 -176.168) 
                         (list -96.4275 -176.192) 
                         (list -96.4509 -176.215) 
                         (list -96.3808 -176.231) 
                         (list -96.4119 -176.262) 
                         (list -96.5133 -176.254) 
                         (list -96.5288 -176.254) 
                         (list -96.8016 -176.386) 
                         (list -96.9731 -176.425) 
                         (list -97.0822 -176.355) 
                         "c"
         )
        (command "pline" (list -97.355 -176.192) "w" 0 0 
                         (list -92.7568 -174.213) 
                         (list -92.7022 -174.205) 
                         (list -92.671 -174.229) 
                         (list -94.0115 -174.813) 
                         (list -94.0037 -174.86) 
                         (list -95.7651 -175.584) 
                         (list -95.7573 -175.654) 
                         (list -97.0588 -176.207) 
                         (list -97.0276 -176.238) 
                         (list -97.1991 -176.262) 
                         (list -97.2692 -176.254) 
                         "c"
         )
        (command "pline" (list -97.5108 -176.114) "w" 0 0 
                         (list -97.6044 -176.036) 
                         (list -97.6199 -176.02) 
                         (list -92.6866 -173.901) 
                         (list -92.6243 -173.901) 
                         (list -92.6009 -173.948) 
                         (list -93.8245 -174.462) 
                         (list -94.0115 -174.525) 
                         (list -94.0115 -174.595) 
                         (list -95.804 -175.319) 
                         (list -95.804 -175.382) 
                         "c"
         )
        (command "pline" (list -97.8148 -175.849) "w" 0 0 
                         (list -92.6321 -173.598) 
                         (list -92.6009 -173.644) 
                         (list -92.6321 -173.676) 
                         (list -94.0271 -174.268) 
                         (list -94.0349 -174.33) 
                         (list -95.7963 -175.047) 
                         (list -95.8274 -175.124) 
                         (list -97.7291 -175.919) 
                         "c"
         )
        (command "pline" (list -92.3612 -173.478) "w" 0 0 
                         (list -92.2564 -173.459) 
                         (list -90.7701 -173.453) 
                         (list -90.7022 -173.496) 
                         (list -90.7084 -173.589) 
                         (list -90.7331 -173.601) 
                         (list -91.1401 -173.601) 
                         (list -91.1401 -174.908) 
                         (list -91.1278 -174.988) 
                         (list -91.1093 -175.124) 
                         (list -91.0723 -175.198) 
                         (list -91.0353 -175.315) 
                         (list -90.9304 -175.401) 
                         (list -90.7824 -175.444) 
                         (list -90.6652 -175.45) 
                         (list -90.4679 -175.463) 
                         (list -90.3137 -175.45) 
                         (list -90.1472 -175.432) 
                         (list -90.0238 -175.401) 
                         (list -89.8882 -175.352) 
                         (list -89.7833 -175.247) 
                         (list -89.7216 -175.117) 
                         (list -89.7093 -175.056) 
                         (list -89.7031 -174.889) 
                         (list -89.7093 -174.544) 
                         (list -89.7093 -173.687) 
                         (list -89.7216 -173.632) 
                         (list -89.7587 -173.607) 
                         (list -89.7772 -173.595) 
                         (list -90.0423 -173.607) 
                         (list -90.1102 -173.576) 
                         (list -90.1102 -173.465) 
                         (list -90.0608 -173.459) 
                         (list -89.2591 -173.447) 
                         (list -89.2406 -173.502) 
                         (list -89.2406 -173.57) 
                         (list -89.3331 -173.601) 
                         (list -89.4256 -173.613) 
                         (list -89.4565 -173.663) 
                         (list -89.4688 -173.712) 
                         (list -89.475 -173.774) 
                         (list -89.4565 -175.025) 
                         (list -89.475 -175.142) 
                         (list -89.512 -175.216) 
                         (list -89.5675 -175.309) 
                         (list -89.6291 -175.382) 
                         (list -89.7155 -175.432) 
                         (list -89.882 -175.5) 
                         (list -90.0238 -175.549) 
                         (list -90.1595 -175.58) 
                         (list -90.215 -175.592) 
                         (list -91.0044 -175.611) 
                         (list -91.0784 -175.598) 
                         (list -91.2573 -175.574) 
                         (list -91.4176 -175.543) 
                         (list -91.615 -175.487) 
                         (list -91.7137 -175.432) 
                         (list -91.7877 -175.407) 
                         (list -91.8432 -175.352) 
                         (list -91.8802 -175.284) 
                         (list -91.9233 -175.204) 
                         (list -91.9542 -175.087) 
                         (list -91.9727 -174.914) 
                         (list -91.9727 -174.723) 
                         (list -91.9727 -173.663) 
                         (list -91.9912 -173.607) 
                         (list -92.022 -173.601) 
                         (list -92.3612 -173.607) 
                         (list -92.3735 -173.558) 
                         "c"
         )
        (command "pline" (list -76.2569 -175.506) "w" 0 0 
                         (list -75.2455 -175.5) 
                         (list -73.679 -174.224) 
                         (list -74.0491 -175.302) 
                         (list -74.1847 -175.487) 
                         (list -73.2473 -175.506) 
                         (list -72.5751 -173.33) 
                         (list -73.5248 -173.342) 
                         (list -76.1336 -175.426) 
                         (list -76.2569 -175.475) 
                         "c"
         )
        (command "pline" (list -72.3144 -174.871) "w" 0 0 
                         (list -72.3514 -174.932) 
                         (list -72.3452 -175.469) 
                         (list -72.2835 -175.506) 
                         (list -72.0985 -175.506) 
                         (list -72.0245 -175.456) 
                         (list -71.9135 -175.401) 
                         (list -71.8271 -175.444) 
                         (list -71.636 -175.493) 
                         (list -71.4078 -175.53) 
                         (list -71.1364 -175.537) 
                         (list -70.8589 -175.53) 
                         (list -70.6492 -175.487) 
                         (list -70.3902 -175.37) 
                         (list -70.1928 -175.21) 
                         (list -70.1127 -175.13) 
                         (list -70.0633 -174.994) 
                         (list -70.0325 -174.828) 
                         (list -70.0387 -174.643) 
                         (list -70.1188 -174.489) 
                         (list -70.1682 -174.396) 
                         (list -70.2668 -174.328) 
                         (list -70.4025 -174.254) 
                         (list -70.5814 -174.193) 
                         (list -70.7726 -174.137) 
                         (list -70.9576 -174.094) 
                         (list -71.1117 -174.07) 
                         (list -71.2783 -174.039) 
                         (list -71.4139 -174.008) 
                         (list -71.5866 -173.983) 
                         (list -71.7038 -173.94) 
                         (list -71.8271 -173.915) 
                         (list -71.8826 -173.885) 
                         (list -71.9258 -173.829) 
                         (list -71.9258 -173.767) 
                         (list -71.9197 -173.718) 
                         (list -71.895 -173.656) 
                         (list -71.821 -173.601) 
                         (list -71.7223 -173.552) 
                         (list -71.6421 -173.527) 
                         (list -71.562 -173.515) 
                         (list -71.4694 -173.484) 
                         (list -71.3214 -173.484) 
                         (list -71.1734 -173.484) 
                         (list -70.9946 -173.509) 
                         (list -70.8466 -173.57) 
                         (list -70.7232 -173.613) 
                         (list -70.6184 -173.749) 
                         (list -70.5382 -173.866) 
                         (list -70.4827 -173.94) 
                         (list -70.4272 -173.965) 
                         (list -70.2977 -173.965) 
                         (list -70.2853 -173.928) 
                         (list -70.2853 -173.398) 
                         (list -70.3347 -173.373) 
                         (list -70.495 -173.385) 
                         (list -70.5444 -173.441) 
                         (list -70.5999 -173.459) 
                         (list -70.643 -173.459) 
                         (list -70.7047 -173.459) 
                         (list -70.7849 -173.422) 
                         (list -70.9822 -173.367) 
                         (list -71.1796 -173.348) 
                         (list -71.3523 -173.342) 
                         (list -71.5188 -173.348) 
                         (list -71.6976 -173.379) 
                         (list -71.8703 -173.453) 
                         (list -72.0183 -173.515) 
                         (list -72.0985 -173.595) 
                         (list -72.2033 -173.693) 
                         (list -72.2773 -173.811) 
                         (list -72.3329 -173.983) 
                         (list -72.3144 -174.131) 
                         (list -72.2773 -174.291) 
                         (list -72.191 -174.384) 
                         (list -72.1047 -174.439) 
                         (list -71.9382 -174.519) 
                         (list -71.7038 -174.6) 
                         (list -71.5064 -174.649) 
                         (list -71.3461 -174.667) 
                         (list -71.2104 -174.674) 
                         (list -71.0439 -174.698) 
                         (list -70.8712 -174.729) 
                         (list -70.6862 -174.778) 
                         (list -70.5752 -174.846) 
                         (list -70.495 -174.932) 
                         (list -70.4519 -175.013) 
                         (list -70.458 -175.136) 
                         (list -70.5444 -175.259) 
                         (list -70.6492 -175.309) 
                         (list -70.7664 -175.37) 
                         (list -70.8774 -175.395) 
                         (list -70.9946 -175.401) 
                         (list -71.1364 -175.419) 
                         (list -71.2968 -175.413) 
                         (list -71.4324 -175.389) 
                         (list -71.6483 -175.346) 
                         (list -71.7716 -175.265) 
                         (list -71.8888 -175.185) 
                         (list -71.9937 -175.08) 
                         (list -72.08 -174.963) 
                         (list -72.117 -174.896) 
                         "c"
         )
        (command "pline" (list -68.0652 -173.354) "w" 0 0 
                         (list -66.8379 -173.348) 
                         (list -66.8317 -173.465) 
                         (list -67.1647 -173.49) 
                         (list -67.3436 -173.509) 
                         (list -68.1947 -174.088) 
                         (list -66.9242 -175.309) 
                         (list -66.8132 -175.333) 
                         (list -66.4802 -175.333) 
                         (list -66.4617 -175.45) 
                         (list -68.2193 -175.469) 
                         (list -68.2317 -175.327) 
                         (list -67.9233 -175.321) 
                         (list -68.8546 -174.439) 
                         (list -68.8607 -174.464) 
                         (list -68.8792 -174.489) 
                         (list -68.8607 -175.309) 
                         (list -68.8237 -175.346) 
                         (list -68.4722 -175.346) 
                         (list -68.4599 -175.438) 
                         (list -68.4907 -175.463) 
                         (list -70.1127 -175.475) 
                         (list -70.125 -175.432) 
                         (list -70.125 -175.358) 
                         (list -70.0695 -175.346) 
                         (list -69.7365 -175.327) 
                         (list -69.755 -173.515) 
                         (list -70.0387 -173.509) 
                         (list -70.125 -173.502) 
                         (list -70.1373 -173.391) 
                         (list -70.0572 -173.373) 
                         (list -68.4845 -173.361) 
                         (list -68.4845 -173.472) 
                         (list -68.5092 -173.502) 
                         (list -68.8546 -173.509) 
                         (list -68.8792 -173.564) 
                         (list -68.8792 -174.31) 
                         (list -68.8484 -174.335) 
                         (list -67.6766 -173.539) 
                         (list -67.7013 -173.484) 
                         (list -68.0035 -173.496) 
                         (list -68.0837 -173.478) 
                         (list -68.0837 -173.379) 
                         "c"
         )
   	(command "style" "ht" "simhei.ttf" "" "" "" "" "" "")
   	(setq c_date (rtos (getvar "CDATE")))
	(setq c_date (strcat (substr c_date 1 4) "/" (substr c_date 5 2) "/" (substr c_date 7 2)))
   	(setq txt_dt (list (cons 0 "TEXT") (cons 1 c_date) (cons 10 (list -65 -176)) (cons 40 3) (cons 7 "ht")))
	(entmake txt_dt)
  )
(prompt "\输入gd运行")
