(defun get_dt_vl (item dt)
  (cdr (assoc item dt))
)
(defun get_point_list(lwp_dt / tmp_dt v_list)
  (setq tmp_dt (member (assoc 10 lwp_dt) lwp_dt))
  (setq v_list nil)
  (while tmp_dt
    (if (setq vtx (get_dt_vl 10 tmp_dt))
        (setq v_list (append v_list (list vtx)))
      )
    (setq tmp_dt (cdr tmp_dt))
    (setq tmp_dt (member (assoc 10 tmp_dt)))
    )
  (setq v_list (append v_list (car v_list)))
  (setq v_list v_list)
  )

(defun int_chk (lwp_dt)  	
  (setq vtx_num (get_dt_vl 90 lwp_dt))
  (setq v_list (get_point_list lwp_dt))	 
  (if (>= vtx_num 4)
    (progn
      (setq p1 (car v_list))
      (setq v_list (cdr v_list))
      (setq p2 (car v_list))
      (setq v_list (cdr v_list))
      (setq p3 (car v_list))
      (setq v_list (cdr v_list))
      (setq int_result (int_judge p1 p2 p3 v_list nil))
    )
    (setq int_result nil)
  )
  (setq int_result int_result)
)
(defun int_judge (p1 p2 p3 v_list jg)
  (if (or jg (= v_list nil))
    (setq result jg)
    (progn      
  (setq p4 (car v_list))
  (setq v_list (cdr v_list))
  (if (= (inters p1 p2 p3 p4 T) nil)
    (progn
      (if v_lsit
	(progn
	(setq rst_list v_lsit)	  
	(setq result (int_judge p2 p3 p4 v_list nil))
	(setq rst_list v_lsit)
	(while rst_dt
	  (setq p3 p4)
	  (setq p4 (get_dt_vl 10 rst_dt))
	  (setq rst_dt (cdr rst_dt))
	  (setq rst_dt (assoc 10 rst_dt) rst_dt)
	  (if (<> (inters p1 p2 p3 p4 T) nil)
	    (setq result T)
	    )
	  )
	)	
	(setq result nil)
      )
    )
    (setq result T)
  )
  )
)
(defun c:s_int_chk ()
  (setq lwp_ss (ssget "x" (list (cons 0 "lwpolyline"))))
  (if lwp_ss
    (progn
      (setq lwp_cnt (sslength lwp_ss))
      (setq cnt_ptr 0)
      (while (< cnt_ptr lwp_cnt)
	(setq lwp_dt (entget (ssname lwp_ss cnt_ptr)))
	(if (int_chk lwp_dt)
	  (progn
	    (setq lwp_dt (subst	(cons 8 "self_inter")
				(assoc 8 lwp_dt)
				lwp_dt
			 )
	    )
	    (entmod lwp_dt)
	  )
	)
	(setq cnt_ptr (1+ cnt_ptr))
      )
    )
  )
)
