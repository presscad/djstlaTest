(defun c:jj () 
        (command "pline" (list 142.064 -204.679) "w" 0 0 
                         (list 142.432 -204.678) 
                         (list 142.434 -204.713) 
                         (list 142.334 -204.72) 
                         (list 142.28 -204.726) 
                         (list 142.025 -204.9) 
                         (list 142.406 -205.266) 
                         (list 142.439 -205.273) 
                         (list 142.539 -205.273) 
                         (list 142.545 -205.308) 
                         (list 142.018 -205.314) 
                         (list 142.014 -205.271) 
                         (list 142.106 -205.27) 
                         (list 141.827 -205.005) 
                         (list 141.825 -205.012) 
                         (list 141.82 -205.02) 
                         (list 141.825 -205.266) 
                         (list 141.836 -205.277) 
                         (list 141.942 -205.277) 
                         (list 141.945 -205.305) 
                         (list 141.936 -205.312) 
                         (list 141.45 -205.316) 
                         (list 141.446 -205.303) 
                         (list 141.446 -205.281) 
                         (list 141.463 -205.277) 
                         (list 141.562 -205.271) 
                         (list 141.557 -204.728) 
                         (list 141.472 -204.726) 
                         (list 141.446 -204.724) 
                         (list 141.442 -204.691) 
                         (list 141.466 -204.685) 
                         (list 141.938 -204.682) 
                         (list 141.938 -204.715) 
                         (list 141.931 -204.724) 
                         (list 141.827 -204.726) 
                         (list 141.82 -204.742) 
                         (list 141.82 -204.966) 
                         (list 141.829 -204.974) 
                         (list 142.18 -204.735) 
                         (list 142.173 -204.718) 
                         (list 142.082 -204.722) 
                         (list 142.058 -204.717) 
                         (list 142.058 -204.687) 
                         "c"
         )
        (command "pline" (list 140.789 -205.135) "w" 0 0 
                         (list 140.778 -205.153) 
                         (list 140.78 -205.314) 
                         (list 140.798 -205.325) 
                         (list 140.854 -205.325) 
                         (list 140.876 -205.31) 
                         (list 140.909 -205.294) 
                         (list 140.935 -205.306) 
                         (list 140.993 -205.321) 
                         (list 141.061 -205.332) 
                         (list 141.142 -205.334) 
                         (list 141.226 -205.332) 
                         (list 141.289 -205.319) 
                         (list 141.366 -205.284) 
                         (list 141.426 -205.236) 
                         (list 141.45 -205.212) 
                         (list 141.464 -205.171) 
                         (list 141.474 -205.122) 
                         (list 141.472 -205.066) 
                         (list 141.448 -205.02) 
                         (list 141.433 -204.992) 
                         (list 141.403 -204.972) 
                         (list 141.363 -204.949) 
                         (list 141.309 -204.931) 
                         (list 141.252 -204.914) 
                         (list 141.196 -204.901) 
                         (list 141.15 -204.894) 
                         (list 141.1 -204.885) 
                         (list 141.059 -204.876) 
                         (list 141.007 -204.868) 
                         (list 140.972 -204.855) 
                         (list 140.935 -204.848) 
                         (list 140.919 -204.839) 
                         (list 140.906 -204.822) 
                         (list 140.906 -204.803) 
                         (list 140.907 -204.789) 
                         (list 140.915 -204.77) 
                         (list 140.937 -204.754) 
                         (list 140.967 -204.739) 
                         (list 140.991 -204.731) 
                         (list 141.015 -204.728) 
                         (list 141.043 -204.718) 
                         (list 141.087 -204.718) 
                         (list 141.131 -204.718) 
                         (list 141.185 -204.726) 
                         (list 141.229 -204.744) 
                         (list 141.266 -204.757) 
                         (list 141.298 -204.798) 
                         (list 141.322 -204.833) 
                         (list 141.339 -204.855) 
                         (list 141.355 -204.863) 
                         (list 141.394 -204.863) 
                         (list 141.398 -204.852) 
                         (list 141.398 -204.693) 
                         (list 141.383 -204.685) 
                         (list 141.335 -204.689) 
                         (list 141.32 -204.706) 
                         (list 141.303 -204.711) 
                         (list 141.29 -204.711) 
                         (list 141.272 -204.711) 
                         (list 141.248 -204.7) 
                         (list 141.189 -204.683) 
                         (list 141.129 -204.678) 
                         (list 141.078 -204.676) 
                         (list 141.028 -204.678) 
                         (list 140.974 -204.687) 
                         (list 140.922 -204.709) 
                         (list 140.878 -204.728) 
                         (list 140.854 -204.752) 
                         (list 140.822 -204.781) 
                         (list 140.8 -204.817) 
                         (list 140.784 -204.868) 
                         (list 140.789 -204.913) 
                         (list 140.8 -204.961) 
                         (list 140.826 -204.988) 
                         (list 140.852 -205.005) 
                         (list 140.902 -205.029) 
                         (list 140.972 -205.053) 
                         (list 141.031 -205.068) 
                         (list 141.08 -205.073) 
                         (list 141.12 -205.075) 
                         (list 141.17 -205.083) 
                         (list 141.222 -205.092) 
                         (list 141.278 -205.107) 
                         (list 141.311 -205.127) 
                         (list 141.335 -205.153) 
                         (list 141.348 -205.177) 
                         (list 141.346 -205.214) 
                         (list 141.32 -205.251) 
                         (list 141.289 -205.266) 
                         (list 141.253 -205.284) 
                         (list 141.22 -205.292) 
                         (list 141.185 -205.294) 
                         (list 141.142 -205.299) 
                         (list 141.094 -205.297) 
                         (list 141.054 -205.29) 
                         (list 140.989 -205.277) 
                         (list 140.952 -205.253) 
                         (list 140.917 -205.229) 
                         (list 140.885 -205.197) 
                         (list 140.859 -205.162) 
                         (list 140.848 -205.142) 
                         "c"
         )
        (command "pline" (list 139.606 -205.325) "w" 0 0 
                         (list 139.91 -205.323) 
                         (list 140.38 -204.94) 
                         (list 140.269 -205.264) 
                         (list 140.228 -205.319) 
                         (list 140.509 -205.325) 
                         (list 140.711 -204.672) 
                         (list 140.426 -204.676) 
                         (list 139.643 -205.301) 
                         (list 139.606 -205.316) 
                         "c"
         )
        (command "pline" (list 134.775 -204.717) "w" 0 0 
                         (list 134.806 -204.711) 
                         (list 135.252 -204.709) 
                         (list 135.273 -204.722) 
                         (list 135.271 -204.75) 
                         (list 135.263 -204.754) 
                         (list 135.141 -204.754) 
                         (list 135.141 -205.146) 
                         (list 135.145 -205.17) 
                         (list 135.151 -205.21) 
                         (list 135.162 -205.233) 
                         (list 135.173 -205.268) 
                         (list 135.204 -205.294) 
                         (list 135.249 -205.306) 
                         (list 135.284 -205.308) 
                         (list 135.343 -205.312) 
                         (list 135.389 -205.308) 
                         (list 135.439 -205.303) 
                         (list 135.476 -205.294) 
                         (list 135.517 -205.279) 
                         (list 135.548 -205.247) 
                         (list 135.567 -205.208) 
                         (list 135.571 -205.19) 
                         (list 135.572 -205.14) 
                         (list 135.571 -205.036) 
                         (list 135.571 -204.779) 
                         (list 135.567 -204.763) 
                         (list 135.556 -204.755) 
                         (list 135.55 -204.752) 
                         (list 135.471 -204.755) 
                         (list 135.45 -204.746) 
                         (list 135.45 -204.713) 
                         (list 135.465 -204.711) 
                         (list 135.706 -204.707) 
                         (list 135.711 -204.724) 
                         (list 135.711 -204.744) 
                         (list 135.683 -204.754) 
                         (list 135.656 -204.757) 
                         (list 135.646 -204.772) 
                         (list 135.643 -204.787) 
                         (list 135.641 -204.805) 
                         (list 135.646 -205.181) 
                         (list 135.641 -205.216) 
                         (list 135.63 -205.238) 
                         (list 135.613 -205.266) 
                         (list 135.595 -205.288) 
                         (list 135.569 -205.303) 
                         (list 135.519 -205.323) 
                         (list 135.476 -205.338) 
                         (list 135.436 -205.347) 
                         (list 135.419 -205.351) 
                         (list 135.182 -205.357) 
                         (list 135.16 -205.353) 
                         (list 135.106 -205.345) 
                         (list 135.058 -205.336) 
                         (list 134.999 -205.319) 
                         (list 134.969 -205.303) 
                         (list 134.947 -205.295) 
                         (list 134.93 -205.279) 
                         (list 134.919 -205.258) 
                         (list 134.906 -205.234) 
                         (list 134.897 -205.199) 
                         (list 134.892 -205.147) 
                         (list 134.892 -205.09) 
                         (list 134.892 -204.772) 
                         (list 134.886 -204.755) 
                         (list 134.877 -204.754) 
                         (list 134.775 -204.755) 
                         (list 134.771 -204.741) 
                         "c"
         )
        (command "pline" (list 133.139 -205.428) "w" 0 0 
                         (list 134.694 -204.753) 
                         (list 134.703 -204.766) 
                         (list 134.694 -204.776) 
                         (list 134.275 -204.954) 
                         (list 134.273 -204.972) 
                         (list 133.744 -205.187) 
                         (list 133.735 -205.21) 
                         (list 133.165 -205.449) 
                         "c"
         )
        (command "pline" (list 133.23 -205.507) "w" 0 0 
                         (list 133.202 -205.484) 
                         (list 133.197 -205.479) 
                         (list 134.677 -204.844) 
                         (list 134.696 -204.844) 
                         (list 134.703 -204.858) 
                         (list 134.336 -205.012) 
                         (list 134.28 -205.031) 
                         (list 134.28 -205.052) 
                         (list 133.742 -205.269) 
                         (list 133.742 -205.288) 
                         "c"
         )
        (command "pline" (list 133.277 -205.531) "w" 0 0 
                         (list 134.656 -204.937) 
                         (list 134.673 -204.935) 
                         (list 134.682 -204.942) 
                         (list 134.28 -205.117) 
                         (list 134.282 -205.131) 
                         (list 133.754 -205.348) 
                         (list 133.756 -205.369) 
                         (list 133.366 -205.535) 
                         (list 133.375 -205.545) 
                         (list 133.324 -205.552) 
                         (list 133.303 -205.549) 
                         "c"
         )
        (command "pline" (list 133.354 -205.577) "w" 0 0 
                         (list 134.647 -205.028) 
                         (list 134.654 -205.031) 
                         (list 134.661 -205.038) 
                         (list 134.656 -205.049) 
                         (list 134.294 -205.199) 
                         (list 134.289 -205.208) 
                         (list 133.756 -205.432) 
                         (list 133.759 -205.447) 
                         (list 133.593 -205.524) 
                         (list 133.555 -205.531) 
                         (list 133.548 -205.538) 
                         (list 133.569 -205.543) 
                         (list 133.56 -205.552) 
                         (list 133.529 -205.549) 
                         (list 133.525 -205.549) 
                         (list 133.443 -205.589) 
                         (list 133.391 -205.601) 
                         (list 133.359 -205.58) 
                         "c"
         )
        (command "pline" (list 133.459 -205.62) "w" 0 0 
                         (list 134.605 -205.136) 
                         (list 134.61 -205.145) 
                         (list 134.614 -205.154) 
                         (list 134.287 -205.288) 
                         (list 134.282 -205.297) 
                         (list 133.929 -205.447) 
                         (list 133.754 -205.519) 
                         (list 133.752 -205.528) 
                         (list 133.752 -205.54) 
                         (list 133.759 -205.549) 
                         (list 133.712 -205.554) 
                         (list 133.534 -205.638) 
                         (list 133.501 -205.645) 
                         (list 133.487 -205.641) 
                         "c"
         )
        (command "pline" (list 133.567 -205.657) "w" 0 0 
                         (list 134.509 -205.255) 
                         (list 134.516 -205.248) 
                         (list 134.539 -205.243) 
                         (list 134.537 -205.257) 
                         (list 134.53 -205.271) 
                         (list 134.303 -205.365) 
                         (list 134.296 -205.39) 
                         (list 133.939 -205.538) 
                         (list 133.932 -205.54) 
                         (list 133.95 -205.549) 
                         (list 133.894 -205.549) 
                         (list 133.789 -205.591) 
                         (list 133.77 -205.594) 
                         (list 133.763 -205.61) 
                         (list 133.761 -205.627) 
                         (list 133.663 -205.669) 
                         (list 133.618 -205.669) 
                         "c"
         )
        (command "pline" (list 133.747 -205.671) "w" 0 0 
                         (list 133.768 -205.655) 
                         (list 134.427 -205.374) 
                         (list 134.434 -205.384) 
                         (list 134.425 -205.395) 
                         (list 134.345 -205.428) 
                         (list 134.303 -205.447) 
                         (list 134.301 -205.465) 
                         (list 134.142 -205.528) 
                         (list 134.126 -205.526) 
                         (list 134.128 -205.538) 
                         (list 134.147 -205.545) 
                         (list 134.095 -205.549) 
                         (list 133.803 -205.673) 
                         "c"
         )
        (command "pline" (list 133.628 -205.156) "w" 0 0 
                         (list 135.203 -204.49) 
                         (list 135.178 -204.467) 
                         (list 135.152 -204.455) 
                         (list 134.57 -204.707) 
                         (list 134.586 -204.719) 
                         (list 134.062 -204.943) 
                         (list 134.034 -204.964) 
                         (list 133.616 -205.147) 
                         "c"
         )
        (command "pline" (list 133.621 -205.07) "w" 0 0 
                         (list 133.651 -205.072) 
                         (list 135.126 -204.429) 
                         (list 135.103 -204.413) 
                         (list 135.066 -204.411) 
                         (list 134.572 -204.621) 
                         (list 134.584 -204.64) 
                         (list 134.044 -204.859) 
                         (list 134.032 -204.873) 
                         (list 134.004 -204.89) 
                         (list 133.623 -205.056) 
                         "c"
         )
        (command "pline" (list 133.644 -204.979) "w" 0 0 
                         (list 135.054 -204.378) 
                         (list 135.033 -204.357) 
                         (list 134.998 -204.355) 
                         (list 134.979 -204.359) 
                         (list 134.598 -204.53) 
                         (list 134.579 -204.541) 
                         (list 134.57 -204.562) 
                         (list 134.044 -204.78) 
                         (list 134.037 -204.794) 
                         (list 133.635 -204.964) 
                         "c"
         )
        (command "pline" (list 133.665 -204.878) "w" 0 0 
                         (list 133.695 -204.878) 
                         (list 133.73 -204.869) 
                         (list 134.97 -204.324) 
                         (list 134.932 -204.313) 
                         (list 134.897 -204.313) 
                         (list 134.565 -204.455) 
                         (list 134.565 -204.474) 
                         (list 134.032 -204.696) 
                         (list 134.023 -204.707) 
                         (list 133.995 -204.724) 
                         (list 133.658 -204.871) 
                         "c"
         )
        (command "pline" (list 133.712 -204.773) "w" 0 0 
                         (list 133.752 -204.763) 
                         (list 134.876 -204.284) 
                         (list 134.839 -204.273) 
                         (list 134.794 -204.268) 
                         (list 134.783 -204.27) 
                         (list 134.572 -204.364) 
                         (list 134.558 -204.397) 
                         (list 134.03 -204.614) 
                         (list 133.976 -204.647) 
                         (list 133.719 -204.757) 
                         (list 133.707 -204.768) 
                         "c"
         )
        (command "pline" (list 133.787 -204.656) "w" 0 0 
                         (list 133.805 -204.658) 
                         (list 134.75 -204.256) 
                         (list 134.708 -204.245) 
                         (list 134.654 -204.247) 
                         (list 134.553 -204.294) 
                         (list 134.56 -204.303) 
                         (list 134.032 -204.523) 
                         (list 134.03 -204.541) 
                         (list 133.787 -204.647) 
                         "c"
         )
        (command "pline" (list 133.908 -204.516) "w" 0 0 
                         (list 133.918 -204.523) 
                         (list 133.95 -204.511) 
                         (list 134.596 -204.24) 
                         (list 134.565 -204.233) 
                         (list 134.532 -204.233) 
                         (list 134.013 -204.45) 
                         (list 134.011 -204.467) 
                         (list 133.903 -204.511) 
                         "c"
         )
        (command "pline" (list 139.005 -205.288) "w" 0 0 
                         (list 138.99 -205.292) 
                         (list 138.992 -205.321) 
                         (list 139.01 -205.325) 
                         (list 139.48 -205.325) 
                         (list 139.493 -205.318) 
                         (list 139.493 -205.288) 
                         (list 139.469 -205.284) 
                         (list 139.364 -205.284) 
                         (list 139.358 -204.737) 
                         (list 139.467 -204.739) 
                         (list 139.486 -204.728) 
                         (list 139.488 -204.704) 
                         (list 139.48 -204.696) 
                         (list 139.463 -204.693) 
                         (list 139.082 -204.694) 
                         (list 138.914 -205.036) 
                         (list 138.907 -205.042) 
                         (list 138.733 -204.696) 
                         (list 138.316 -204.698) 
                         (list 138.313 -204.733) 
                         (list 138.329 -204.741) 
                         (list 138.44 -204.741) 
                         (list 138.442 -205.251) 
                         (list 138.438 -205.268) 
                         (list 138.429 -205.286) 
                         (list 138.401 -205.29) 
                         (list 138.374 -205.295) 
                         (list 138.374 -205.318) 
                         (list 138.377 -205.325) 
                         (list 138.627 -205.329) 
                         (list 138.636 -205.321) 
                         (list 138.636 -205.301) 
                         (list 138.629 -205.29) 
                         (list 138.525 -205.288) 
                         (list 138.514 -205.271) 
                         (list 138.507 -205.253) 
                         (list 138.501 -204.768) 
                         (list 138.507 -204.77) 
                         (list 138.764 -205.308) 
                         (list 138.779 -205.325) 
                         (list 138.836 -205.323) 
                         (list 139.099 -204.778) 
                         (list 139.108 -204.763) 
                         (list 139.116 -204.783) 
                         (list 139.117 -205.279) 
                         (list 139.116 -205.286) 
                         (list 139.018 -205.288) 
                         "c"
         )
        (command "pline" (list 135.759 -204.709) "w" 0 0 
                         (list 135.761 -204.746) 
                         (list 135.8 -204.748) 
                         (list 135.82 -204.752) 
                         (list 135.822 -205.294) 
                         (list 135.817 -205.301) 
                         (list 135.709 -205.301) 
                         (list 135.706 -205.308) 
                         (list 135.706 -205.332) 
                         (list 135.715 -205.338) 
                         (list 135.728 -205.342) 
                         (list 136.203 -205.34) 
                         (list 136.214 -205.332) 
                         (list 136.216 -205.306) 
                         (list 136.205 -205.295) 
                         (list 136.078 -205.294) 
                         (list 136.076 -205.081) 
                         (list 136.079 -205.06) 
                         (list 136.085 -205.053) 
                         (list 136.103 -205.053) 
                         (list 136.127 -205.051) 
                         (list 136.148 -205.051) 
                         (list 136.227 -205.049) 
                         (list 136.29 -205.048) 
                         (list 136.359 -205.049) 
                         (list 136.399 -205.04) 
                         (list 136.464 -205.029) 
                         (list 136.514 -205.011) 
                         (list 136.564 -204.981) 
                         (list 136.594 -204.952) 
                         (list 136.614 -204.918) 
                         (list 136.616 -204.896) 
                         (list 136.62 -204.865) 
                         (list 136.609 -204.831) 
                         (list 136.596 -204.803) 
                         (list 136.575 -204.778) 
                         (list 136.533 -204.755) 
                         (list 136.496 -204.737) 
                         (list 136.451 -204.728) 
                         (list 136.403 -204.722) 
                         (list 136.38 -204.721) 
                         (list 136.072 -204.75) 
                         (list 136.153 -204.748) 
                         (list 136.2 -204.744) 
                         (list 136.257 -204.748) 
                         (list 136.3 -204.763) 
                         (list 136.32 -204.787) 
                         (list 136.333 -204.817) 
                         (list 136.338 -204.85) 
                         (list 136.337 -204.89) 
                         (list 136.34 -204.924) 
                         (list 136.333 -204.953) 
                         (list 136.333 -204.961) 
                         (list 136.312 -204.996) 
                         (list 136.29 -205.007) 
                         (list 136.275 -205.011) 
                         (list 136.231 -205.011) 
                         (list 136.078 -205.011) 
                         (list 136.078 -205.005) 
                         (list 136.072 -204.75) 
                         (list 136.38 -204.721) 
                         (list 136.346 -204.718) 
                         (list 136.294 -204.711) 
                         (list 136.233 -204.709) 
                         (list 136.168 -204.706) 
                         "c"
         )
        (command "pline" (list 138.327 -205.336) "w" 0 0 
                         (list 138.337 -205.318) 
                         (list 138.329 -205.294) 
                         (list 138.281 -205.286) 
                         (list 138.268 -205.264) 
                         (list 138.268 -205.222) 
                         (list 138.263 -205.188) 
                         (list 138.255 -205.146) 
                         (list 138.244 -205.111) 
                         (list 138.216 -205.079) 
                         (list 138.187 -205.059) 
                         (list 138.139 -205.033) 
                         (list 138.091 -205.022) 
                         (list 138.068 -205.014) 
                         (list 138.018 -205.011) 
                         (list 137.985 -205.005) 
                         (list 137.98 -205.003) 
                         (list 138.009 -205.0) 
                         (list 138.05 -204.996) 
                         (list 138.107 -204.988) 
                         (list 138.155 -204.977) 
                         (list 138.211 -204.959) 
                         (list 138.259 -204.927) 
                         (list 138.281 -204.898) 
                         (list 138.303 -204.842) 
                         (list 138.294 -204.803) 
                         (list 138.266 -204.772) 
                         (list 138.231 -204.75) 
                         (list 138.229 -204.749) 
                         (list 138.016 -204.854) 
                         (list 138.017 -204.918) 
                         (list 138.01 -204.94) 
                         (list 138.002 -204.949) 
                         (list 137.982 -204.968) 
                         (list 137.963 -204.972) 
                         (list 137.943 -204.976) 
                         (list 137.893 -204.977) 
                         (list 137.773 -204.974) 
                         (list 137.762 -204.964) 
                         (list 137.765 -204.748) 
                         (list 137.773 -204.742) 
                         (list 137.939 -204.742) 
                         (list 137.971 -204.746) 
                         (list 137.989 -204.757) 
                         (list 137.999 -204.77) 
                         (list 138.004 -204.787) 
                         (list 138.01 -204.798) 
                         (list 138.015 -204.809) 
                         (list 138.016 -204.854) 
                         (list 138.229 -204.749) 
                         (list 138.176 -204.728) 
                         (list 138.159 -204.722) 
                         (list 138.067 -204.711) 
                         (list 138.024 -204.711) 
                         (list 137.948 -204.704) 
                         (list 137.813 -204.7) 
                         (list 137.417 -204.704) 
                         (list 137.402 -204.706) 
                         (list 137.401 -204.739) 
                         (list 137.417 -204.742) 
                         (list 137.51 -204.744) 
                         (list 137.515 -205.294) 
                         (list 137.423 -205.292) 
                         (list 137.425 -205.201) 
                         (list 137.425 -205.177) 
                         (list 137.432 -205.173) 
                         (list 137.428 -205.122) 
                         (list 137.415 -205.118) 
                         (list 137.378 -205.116) 
                         (list 137.36 -205.162) 
                         (list 137.338 -205.203) 
                         (list 137.301 -205.24) 
                         (list 137.273 -205.264) 
                         (list 137.249 -205.273) 
                         (list 137.206 -205.282) 
                         (list 137.164 -205.297) 
                         (list 137.08 -205.297) 
                         (list 136.929 -205.295) 
                         (list 136.92 -205.284) 
                         (list 136.918 -205.027) 
                         (list 136.957 -205.036) 
                         (list 136.999 -205.044) 
                         (list 137.048 -205.053) 
                         (list 137.09 -205.068) 
                         (list 137.105 -205.09) 
                         (list 137.116 -205.112) 
                         (list 137.118 -205.149) 
                         (list 137.127 -205.155) 
                         (list 137.175 -205.157) 
                         (list 137.179 -205.149) 
                         (list 137.177 -204.877) 
                         (list 137.168 -204.874) 
                         (list 137.123 -204.876) 
                         (list 137.114 -204.881) 
                         (list 137.11 -204.905) 
                         (list 137.107 -204.924) 
                         (list 137.099 -204.944) 
                         (list 137.081 -204.955) 
                         (list 137.06 -204.972) 
                         (list 137.051 -204.979) 
                         (list 137.012 -204.983) 
                         (list 136.986 -204.985) 
                         (list 136.92 -204.985) 
                         (list 136.92 -204.742) 
                         (list 137.011 -204.741) 
                         (list 137.06 -204.744) 
                         (list 137.134 -204.744) 
                         (list 137.171 -204.752) 
                         (list 137.205 -204.759) 
                         (list 137.231 -204.77) 
                         (list 137.255 -204.79) 
                         (list 137.283 -204.822) 
                         (list 137.301 -204.841) 
                         (list 137.319 -204.865) 
                         (list 137.336 -204.876) 
                         (list 137.36 -204.879) 
                         (list 137.384 -204.876) 
                         (list 137.384 -204.846) 
                         (list 137.384 -204.704) 
                         (list 136.568 -204.706) 
                         (list 136.565 -204.715) 
                         (list 136.566 -204.737) 
                         (list 136.574 -204.748) 
                         (list 136.666 -204.748) 
                         (list 136.666 -205.292) 
                         (list 136.555 -205.295) 
                         (list 136.552 -205.308) 
                         (list 136.55 -205.33) 
                         (list 136.565 -205.334) 
                         (list 137.895 -205.33) 
                         (list 137.9 -205.323) 
                         (list 137.899 -205.297) 
                         (list 137.893 -205.292) 
                         (list 137.773 -205.29) 
                         (list 137.767 -205.022) 
                         (list 137.773 -205.016) 
                         (list 137.839 -205.02) 
                         (list 137.876 -205.024) 
                         (list 137.904 -205.033) 
                         (list 137.934 -205.048) 
                         (list 137.95 -205.062) 
                         (list 137.967 -205.092) 
                         (list 137.976 -205.109) 
                         (list 137.98 -205.138) 
                         (list 137.986 -205.181) 
                         (list 137.987 -205.216) 
                         (list 138.0 -205.262) 
                         (list 138.021 -205.282) 
                         (list 138.05 -205.306) 
                         (list 138.093 -205.325) 
                         (list 138.143 -205.338) 
                         (list 138.171 -205.343) 
                         (list 138.326 -205.34) 
                         "c"
         )
   	(command "style" "ht" "simhei.ttf" "" "" "" "" "" "")
   	(setq c_date (rtos (getvar "CDATE")))
	(setq c_date (strcat (substr c_date 1 4) "/" (substr c_date 5 2) "/" (substr c_date 7 2)))
   	(setq txt_dt (list (cons 0 "TEXT") (cons 1 c_date) (cons 10 (list 144 -205.3)) (cons 40 0.9) (cons 7 "ht")))
	(entmake txt_dt)
  )
(prompt "\输入jj运行")
