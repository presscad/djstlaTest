(defun c:CRT()  
  (defun ph0(ph0_n)
    (if (= ph0_n 0)
      (setq ph0_ph 0)
      (progn
	(setq ph0_m (- ph0_n 1))
	(setq ph0_cgm 0)
	(repeat (- ph0_n 1)
	  (setq ph0_cgm (+ ph0_cgm (ph0 ph0_m)))
	  (setq ph0_m (1- ph0_m))
	)
	(setq ph0_ph (+ 0.650 (* 3.32 (* 0.000001 (* ph0_cgm ph0_cgm)))))
	)
      )
    )
  (defun ph145(ph145_n)
    (if (= ph145_n 0)
      (setq ph145_ph 0)
      (progn
	(setq ph145_m (- ph145_n 1))
	(setq ph145_cgm 0)
	(repeat (- ph145_n 1)
	  (setq ph145_cgm (+ ph145_cgm (ph145 ph145_m)))
	  (setq ph145_m (1- ph145_m))
	)
	(setq ph145_ph (+ 0.652 (* 3.32 (* 0.000001 (* ph145_cgm ph145_cgm)))))
	)
      )
    )
  (defun get_r(r_n)
    (setq cgm_r 0)
    (setq rad_m (1- r_n))
    (setq phn145 (ph145 r_n))
    (repeat r_n
      (setq cgm_r (+ cgm_r (- (ph0 rad_m) phn145)))
      (setq rad_m (1- rad_m))
      )
    (setq rad (/ (+ (* cgm_r cgm_r) 21025) (* cgm_r 2)))   
    )      
  (defun draw_ct()
    (setq p1 (list -0.035 -0.25)
	  p2 (list 0.035 -0.25)
	  p3 (list 0.035 0.25)
	  p4 (list -0.035 0.25)
	  )    
    (command "pline" p1 p2 p3 p4 "c")
    (command "array" "l" "" "r" "146" "1" "0.7")
  )
  (defun draw_MN(n x_sum)
    (setq pv 0.7)
    (setq p0 (ph0 n))
    (setq p145 (ph145 n))
    (setq rad_n (abs (get_r n)))
    (setq x (+ x_sum p0))
    (setq d (+ 0.07 (* 5.97 (* (* x x) 0.0000001))))
    (setq b (+ 0.20 (* 4.07 (* (* x x) 0.0000001))))
    (setq L (- pv b))
    (setq array_pt (list (+ x rad_n) 0))    
    (if	(= (- (/ n 2.0) (/ n 2)) 0)
      (progn
	(setq Y_ct -0.7)
	(repeat	146
	  (setq y_ct (+ y_ct 0.7))
	  (setq at_vl (sqrt (- (* rad_n rad_n) (* y_ct y_ct))))
	  (setq ceta (atan (/ y_ct at_vl)))
	  (setq x_ct (+ x (- rad_n at_vl)))
	  (setq	p1 (list
		     (-	(- x_ct (/ (* (sin ceta) l) 2.0))
			(/ (* (cos ceta) d) 2.0)
		     )
		     (+	(- y_ct (/ (* (cos ceta) l) 2.0))
			(/ (* (sin ceta) d) 2.0)
		     )
		   )
		p2 (list
		     (+	(- x_ct (/ (* (sin ceta) l) 2.0))
			(/ (* (cos ceta) d) 2.0)
		     )
		     (-	(- y_ct (/ (* (cos ceta) l) 2.0))
			(/ (* (sin ceta) d) 2.0)
		     )
		   )
		p3 (list
		     (+	(+ x_ct (/ (* (sin ceta) l) 2.0))
			(/ (* (cos ceta) d) 2.0)
		     )
		     (-	(+ y_ct (/ (* (cos ceta) l) 2.0))
			(/ (* (sin ceta) d) 2.0)
		     )
		   )
		p4 (list
		     (-	(+ x_ct (/ (* (sin ceta) l) 2.0))
			(/ (* (cos ceta) d) 2.0)
		     )
		     (+	(+ y_ct (/ (* (cos ceta) l) 2.0))
			(/ (* (sin ceta) d) 2.0)
		     )
		   )
	  )
	  (command "pline" p1 p2 p3 p4 "c")
	)
      )
      (progn
	(setq Y_ct -0.35)
	(repeat	146
	  (setq y_ct (+ y_ct 0.7))
	  (setq at_vl (sqrt (- (* rad_n rad_n) (* y_ct y_ct))))
	  (setq ceta (atan (/ y_ct at_vl)))
	  (setq x_ct (+ x (- rad_n at_vl)))
	  (setq	p1 (list
		     (-	(- x_ct (/ (* (sin ceta) l) 2.0))
			(/ (* (cos ceta) d) 2.0)
		     )
		     (+	(- y_ct (/ (* (cos ceta) l) 2.0))
			(/ (* (sin ceta) d) 2.0)
		     )
		   )
		p2 (list
		     (+	(- x_ct (/ (* (sin ceta) l) 2.0))
			(/ (* (cos ceta) d) 2.0)
		     )
		     (-	(- y_ct (/ (* (cos ceta) l) 2.0))
			(/ (* (sin ceta) d) 2.0)
		     )
		   )
		p3 (list
		     (+	(+ x_ct (/ (* (sin ceta) l) 2.0))
			(/ (* (cos ceta) d) 2.0)
		     )
		     (-	(+ y_ct (/ (* (cos ceta) l) 2.0))
			(/ (* (sin ceta) d) 2.0)
		     )
		   )
		p4 (list
		     (-	(+ x_ct (/ (* (sin ceta) l) 2.0))
			(/ (* (cos ceta) d) 2.0)
		     )
		     (+	(+ y_ct (/ (* (cos ceta) l) 2.0))
			(/ (* (sin ceta) d) 2.0)
		     )
		   )
	  )
	  (command "pline" p1 p2 p3 p4 "c")
	)
      )
    )
    (setq x x)
    )
  (draw_ct)
  (setq cnt 1)
  (setq x_sum 0)
  (while (< x_sum 192.25)
    (setq x_sum (draw_mn cnt x_sum))
    (setq cnt (1+ cnt))
    )
  )
