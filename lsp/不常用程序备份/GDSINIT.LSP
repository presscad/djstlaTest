(defun gd16 () 
        (command "pline" (list -111.124 -188.823) "w" 0 0 
                         (list -111.172 -188.876) 
                         (list -111.138 -188.911) 
                         (list -111.104 -188.948) 
                         (list -111.072 -188.985) 
                         (list -111.04 -189.023) 
                         (list -111.01 -189.062) 
                         (list -110.982 -189.103) 
                         (list -110.954 -189.144) 
                         (list -110.881 -188.943) 
                         (list -110.679 -189.017) 
                         (list -110.599 -188.795) 
                         (list -110.382 -188.874) 
                         (list -110.3 -188.648) 
                         (list -110.088 -188.725) 
                         (list -110.015 -188.523) 
                         (list -109.799 -188.602) 
                         (list -109.716 -188.376) 
                         (list -109.465 -188.467) 
                         (list -109.513 -188.379) 
                         (list -109.564 -188.292) 
                         (list -109.617 -188.207) 
                         (list -109.673 -188.123) 
                         (list -109.731 -188.041) 
                         (list -109.792 -187.961) 
                         (list -109.88 -188.288) 
                         (list -110.08 -188.234) 
                         (list -110.136 -188.443) 
                         (list -110.331 -188.391) 
                         (list -110.381 -188.578) 
                         (list -110.582 -188.524) 
                         (list -110.638 -188.733) 
                         (list -110.825 -188.683) 
                         (list -110.88 -188.888) 
                         "c"
         )
        (command "pline" (list -110.174 -189.605) "w" 0 0 
                         (list -110.264 -189.798) 
                         (list -109.178 -189.663) 
                         (list -109.179 -189.588) 
                         (list -109.183 -189.512) 
                         (list -109.189 -189.436) 
                         (list -109.418 -189.33) 
                         (list -109.545 -189.602) 
                         (list -109.8 -189.483) 
                         (list -109.913 -189.727) 
                         "c"
         )
        (command "pline" (list -110.38 -189.45) "w" 0 0 
                         (list -110.607 -189.367) 
                         (list -110.698 -189.616) 
                         (list -110.813 -189.574) 
                         (list -110.809 -189.611) 
                         (list -110.807 -189.649) 
                         (list -110.806 -189.686) 
                         (list -110.807 -189.723) 
                         (list -110.808 -189.76) 
                         (list -110.785 -189.712) 
                         (list -110.568 -189.813) 
                         (list -110.579 -189.837) 
                         (list -110.427 -189.819) 
                         (list -110.519 -189.776) 
                         (list -110.417 -189.559) 
                         (list -110.156 -189.68) 
                         (list -110.029 -189.408) 
                         (list -109.774 -189.527) 
                         (list -109.661 -189.283) 
                         (list -109.4 -189.405) 
                         (list -109.273 -189.132) 
                         (list -109.23 -189.152) 
                         (list -109.249 -189.064) 
                         (list -109.271 -188.977) 
                         (list -109.296 -188.89) 
                         (list -109.324 -188.804) 
                         (list -109.387 -188.978) 
                         (list -109.631 -188.889) 
                         (list -109.723 -189.144) 
                         (list -109.961 -189.057) 
                         (list -110.044 -189.284) 
                         (list -110.287 -189.196) 
                         "c"
         )
        (command "pline" (list -110.401 -188.815) "w" 0 0 
                         (list -110.484 -189.041) 
                         (list -110.686 -188.968) 
                         (list -110.767 -189.189) 
                         (list -110.972 -189.114) 
                         (list -110.954 -189.144) 
                         (list -110.938 -189.174) 
                         (list -110.922 -189.204) 
                         (list -110.907 -189.235) 
                         (list -110.893 -189.266) 
                         (list -110.88 -189.298) 
                         (list -110.868 -189.33) 
                         (list -110.857 -189.363) 
                         (list -110.848 -189.396) 
                         (list -110.827 -189.339) 
                         (list -110.6 -189.422) 
                         (list -110.509 -189.173) 
                         (list -110.265 -189.262) 
                         (list -110.173 -189.007) 
                         (list -109.935 -189.094) 
                         (list -109.852 -188.867) 
                         (list -109.609 -188.955) 
                         (list -109.516 -188.701) 
                         (list -109.337 -188.766) 
                         (list -109.367 -188.686) 
                         (list -109.4 -188.607) 
                         (list -109.435 -188.529) 
                         (list -109.472 -188.452) 
                         (list -109.512 -188.377) 
                         (list -109.602 -188.622) 
                         (list -109.818 -188.543) 
                         (list -109.9 -188.769) 
                         (list -110.112 -188.692) 
                         (list -110.185 -188.894) 
                         "c"
         )
        (command "pline" (list -111.463 -188.69) "w" 0 0 
                         (list -111.416 -188.715) 
                         (list -111.37 -188.742) 
                         (list -111.326 -188.77) 
                         (list -111.282 -188.799) 
                         (list -111.239 -188.83) 
                         (list -111.198 -188.863) 
                         (list -111.157 -188.897) 
                         (list -111.118 -188.932) 
                         (list -111.08 -188.969) 
                         (list -111.002 -188.676) 
                         (list -110.815 -188.726) 
                         (list -110.76 -188.522) 
                         (list -110.56 -188.575) 
                         (list -110.504 -188.366) 
                         (list -110.308 -188.419) 
                         (list -110.258 -188.232) 
                         (list -110.058 -188.285) 
                         (list -110.002 -188.076) 
                         (list -109.634 -188.175) 
                         (list -109.71 -188.073) 
                         (list -109.79 -187.973) 
                         (list -109.872 -187.876) 
                         (list -109.958 -187.782) 
                         (list -110.046 -187.69) 
                         (list -110.084 -187.905) 
                         (list -110.246 -187.876) 
                         (list -110.281 -188.077) 
                         (list -110.465 -188.045) 
                         (list -110.499 -188.237) 
                         (list -110.678 -188.205) 
                         (list -110.708 -188.377) 
                         (list -110.892 -188.344) 
                         (list -110.926 -188.536) 
                         (list -111.098 -188.506) 
                         (list -111.131 -188.694) 
                         (list -111.442 -188.639) 
                         "c"
         )
        (command "pline" (list -111.293 -190.614) "w" 0 0 
                         (list -110.971 -190.935) 
                         (list -110.883 -191.172) 
                         (list -110.15 -191.76) 
                         (list -109.44 -192.415) 
                         (list -109.159 -189.722) 
                         (list -111.836 -190.04) 
                         "c"
         )
        (command "pline" (list -113.599 -188.878) "w" 0 0 
                         (list -113.768 -188.625) 
                         (list -113.468 -188.691) 
                         "c"
         )
        (command "pline" (list -113.852 -190.593) "w" 0 0 
                         (list -113.84 -190.586) 
                         (list -113.828 -190.58) 
                         (list -113.816 -190.575) 
                         (list -113.805 -190.57) 
                         (list -113.795 -190.566) 
                         (list -113.784 -190.563) 
                         (list -113.775 -190.561) 
                         (list -113.765 -190.559) 
                         (list -113.756 -190.558) 
                         (list -113.747 -190.557) 
                         (list -113.739 -190.558) 
                         (list -113.73 -190.559) 
                         (list -113.722 -190.56) 
                         (list -113.714 -190.562) 
                         (list -113.707 -190.565) 
                         (list -113.7 -190.568) 
                         (list -113.692 -190.573) 
                         (list -113.685 -190.577) 
                         (list -113.679 -190.582) 
                         (list -113.672 -190.587) 
                         (list -113.665 -190.594) 
                         (list -113.659 -190.6) 
                         (list -113.653 -190.607) 
                         (list -113.646 -190.615) 
                         (list -113.64 -190.623) 
                         (list -113.634 -190.631) 
                         (list -113.628 -190.64) 
                         (list -113.622 -190.65) 
                         (list -113.615 -190.659) 
                         (list -113.609 -190.67) 
                         (list -113.603 -190.68) 
                         (list -113.597 -190.691) 
                         (list -113.848 -190.836) 
                         (list -113.856 -190.84) 
                         (list -113.863 -190.843) 
                         (list -113.87 -190.844) 
                         (list -113.877 -190.844) 
                         (list -113.889 -190.842) 
                         (list -113.9 -190.836) 
                         (list -113.909 -190.829) 
                         (list -113.917 -190.82) 
                         (list -113.923 -190.812) 
                         (list -113.928 -190.804) 
                         (list -113.932 -190.796) 
                         (list -113.935 -190.789) 
                         (list -113.939 -190.781) 
                         (list -113.942 -190.774) 
                         (list -113.947 -190.76) 
                         (list -113.95 -190.745) 
                         (list -113.952 -190.731) 
                         (list -113.952 -190.718) 
                         (list -113.95 -190.704) 
                         (list -113.946 -190.691) 
                         (list -113.941 -190.678) 
                         (list -113.934 -190.665) 
                         (list -113.93 -190.659) 
                         (list -113.925 -190.652) 
                         (list -113.92 -190.646) 
                         (list -113.914 -190.64) 
                         (list -113.908 -190.634) 
                         (list -113.902 -190.628) 
                         (list -113.895 -190.622) 
                         (list -113.887 -190.616) 
                         (list -113.879 -190.61) 
                         (list -113.87 -190.604) 
                         (list -113.861 -190.599) 
                         "c"
         )
        (command "pline" (list -112.695 -191.877) "w" 0 0 
                         (list -112.702 -191.877) 
                         (list -112.708 -191.876) 
                         (list -112.715 -191.874) 
                         (list -112.723 -191.872) 
                         (list -112.731 -191.87) 
                         (list -112.739 -191.867) 
                         (list -112.75 -191.863) 
                         (list -112.761 -191.857) 
                         (list -112.771 -191.85) 
                         (list -112.78 -191.842) 
                         (list -112.788 -191.832) 
                         (list -112.795 -191.822) 
                         (list -112.801 -191.81) 
                         (list -112.806 -191.798) 
                         (list -112.81 -191.784) 
                         (list -112.813 -191.77) 
                         (list -112.814 -191.754) 
                         (list -112.815 -191.738) 
                         (list -112.814 -191.729) 
                         (list -112.813 -191.721) 
                         (list -112.812 -191.712) 
                         (list -112.811 -191.703) 
                         (list -112.809 -191.693) 
                         (list -112.807 -191.684) 
                         (list -112.804 -191.674) 
                         (list -112.801 -191.664) 
                         (list -112.796 -191.649) 
                         (list -112.79 -191.635) 
                         (list -112.784 -191.62) 
                         (list -112.776 -191.606) 
                         (list -112.768 -191.592) 
                         (list -112.758 -191.58) 
                         (list -112.747 -191.569) 
                         (list -112.735 -191.559) 
                         (list -112.729 -191.554) 
                         (list -112.722 -191.55) 
                         (list -112.715 -191.546) 
                         (list -112.707 -191.543) 
                         (list -112.699 -191.54) 
                         (list -112.69 -191.538) 
                         (list -112.681 -191.536) 
                         (list -112.672 -191.535) 
                         (list -112.663 -191.535) 
                         (list -112.652 -191.534) 
                         (list -112.642 -191.535) 
                         (list -112.631 -191.536) 
                         (list -112.619 -191.538) 
                         (list -112.607 -191.54) 
                         (list -112.594 -191.543) 
                         (list -112.581 -191.547) 
                         (list -112.561 -191.554) 
                         (list -112.652 -191.842) 
                         (list -112.655 -191.85) 
                         (list -112.658 -191.857) 
                         (list -112.661 -191.862) 
                         (list -112.665 -191.867) 
                         (list -112.674 -191.874) 
                         (list -112.684 -191.877) 
                         (list -112.689 -191.878) 
                         "c"
         )
        (command "pline" (list -125.085 -190.987) "w" 0 0 
                         (list -125.447 -190.987) 
                         (list -126.206 -190.987) 
                         (list -126.206 -190.404) 
                         (list -125.447 -190.404) 
                         (list -125.428 -190.136) 
                         (list -126.196 -190.136) 
                         (list -126.196 -189.655) 
                         (list -125.428 -189.655) 
                         (list -125.419 -189.368) 
                         (list -126.206 -189.368) 
                         (list -126.206 -188.869) 
                         (list -126.53 -188.878) 
                         (list -126.53 -191.005) 
                         (list -127.141 -191.005) 
                         (list -127.141 -188.878) 
                         (list -126.53 -188.878) 
                         (list -126.206 -188.869) 
                         (list -125.419 -188.869) 
                         (list -125.419 -189.368) 
                         (list -125.428 -189.655) 
                         (list -125.428 -190.136) 
                         (list -125.447 -190.404) 
                         (list -125.447 -190.987) 
                         (list -125.085 -190.987) 
                         (list -125.085 -188.869) 
                         (list -124.484 -188.869) 
                         (list -124.484 -190.987) 
                         (list -124.493 -191.264) 
                         (list -124.474 -191.533) 
                         (list -124.123 -191.523) 
                         (list -124.113 -188.591) 
                         (list -125.724 -188.6) 
                         (list -125.585 -187.971) 
                         (list -123.752 -187.981) 
                         (list -123.762 -187.666) 
                         (list -127.863 -187.657) 
                         (list -127.854 -187.666) 
                         (list -127.863 -187.981) 
                         (list -125.983 -187.971) 
                         (list -126.104 -188.591) 
                         (list -127.511 -188.591) 
                         (list -127.511 -191.533) 
                         (list -127.159 -191.542) 
                         (list -127.15 -191.274) 
                         (list -124.493 -191.264) 
                         (list -124.484 -190.987) 
                         "c"
         )
        (command "pline" (list -131.929 -189.021) "w" 0 0 
                         (list -131.422 -189.017) 
                         (list -131.422 -189.794) 
                         (list -131.926 -189.792) 
                         (list -131.922 -190.07) 
                         (list -131.431 -190.053) 
                         (list -131.422 -190.996) 
                         (list -131.533 -191.061) 
                         (list -131.82 -191.052) 
                         (list -131.718 -191.449) 
                         (list -131.581 -191.425) 
                         (list -131.445 -191.397) 
                         (list -131.31 -191.366) 
                         (list -131.302 -191.364) 
                         (list -131.294 -191.362) 
                         (list -131.286 -191.359) 
                         (list -131.278 -191.356) 
                         (list -131.271 -191.353) 
                         (list -131.263 -191.349) 
                         (list -131.256 -191.345) 
                         (list -131.248 -191.341) 
                         (list -131.241 -191.337) 
                         (list -131.234 -191.333) 
                         (list -131.227 -191.328) 
                         (list -131.22 -191.323) 
                         (list -131.214 -191.318) 
                         (list -131.207 -191.312) 
                         (list -131.201 -191.307) 
                         (list -131.195 -191.301) 
                         (list -131.189 -191.295) 
                         (list -131.184 -191.288) 
                         (list -131.179 -191.282) 
                         (list -131.173 -191.275) 
                         (list -131.169 -191.269) 
                         (list -131.164 -191.262) 
                         (list -131.159 -191.254) 
                         (list -131.155 -191.247) 
                         (list -131.151 -191.24) 
                         (list -131.148 -191.232) 
                         (list -131.144 -191.225) 
                         (list -131.141 -191.217) 
                         (list -131.138 -191.209) 
                         (list -131.136 -191.201) 
                         (list -131.133 -191.193) 
                         (list -131.131 -191.185) 
                         (list -131.13 -191.177) 
                         (list -131.128 -191.168) 
                         (list -131.127 -191.16) 
                         (list -131.126 -191.152) 
                         (list -131.126 -191.143) 
                         (list -131.125 -191.135) 
                         (list -131.107 -187.694) 
                         (list -132.245 -187.685) 
                         (list -132.227 -189.914) 
                         (list -132.228 -190.0) 
                         (list -132.231 -190.087) 
                         (list -132.238 -190.173) 
                         (list -132.247 -190.259) 
                         (list -132.26 -190.345) 
                         (list -132.275 -190.43) 
                         (list -132.293 -190.515) 
                         (list -132.314 -190.599) 
                         (list -132.338 -190.682) 
                         (list -132.364 -190.765) 
                         (list -132.393 -190.846) 
                         (list -132.425 -190.927) 
                         (list -132.46 -191.006) 
                         (list -132.498 -191.084) 
                         (list -132.537 -191.161) 
                         (list -132.58 -191.237) 
                         (list -132.625 -191.311) 
                         (list -132.292 -191.459) 
                         (list -132.243 -191.364) 
                         (list -132.198 -191.267) 
                         (list -132.156 -191.169) 
                         (list -132.117 -191.07) 
                         (list -132.082 -190.969) 
                         (list -132.05 -190.867) 
                         (list -132.022 -190.764) 
                         (list -131.997 -190.66) 
                         (list -131.976 -190.556) 
                         (list -131.958 -190.45) 
                         (list -131.945 -190.354) 
                         (list -131.935 -190.257) 
                         (list -131.927 -190.159) 
                         (list -131.921 -190.062) 
                         (list -131.94 -187.962) 
                         (list -131.422 -187.962) 
                         (list -131.422 -188.739) 
                         (list -131.936 -188.736) 
                         "c"
         )
        (command "pline" (list -128.968 -188.832) "w" 0 0 
                         (list -128.968 -189.155) 
                         (list -128.977 -189.414) 
                         (list -128.977 -189.71) 
                         (list -130.422 -189.71) 
                         (list -130.422 -189.414) 
                         (list -128.977 -189.414) 
                         (list -128.968 -189.155) 
                         (list -130.422 -189.155) 
                         (list -130.422 -188.832) 
                         (list -128.968 -188.832) 
                         (list -129.428 -188.573) 
                         (list -129.947 -188.573) 
                         (list -129.947 -188.163) 
                         (list -129.428 -188.163) 
                         (list -129.422 -187.925) 
                         (list -129.959 -187.916) 
                         (list -129.95 -187.444) 
                         (list -130.255 -187.453) 
                         (list -130.264 -187.444) 
                         (list -130.255 -187.897) 
                         (list -130.894 -187.888) 
                         (list -130.875 -188.175) 
                         (list -130.246 -188.156) 
                         (list -130.255 -188.582) 
                         (list -130.736 -188.591) 
                         (list -130.727 -189.969) 
                         (list -129.885 -189.969) 
                         (list -129.922 -190.349) 
                         (list -130.922 -190.349) 
                         (list -130.922 -190.635) 
                         (list -130.005 -190.626) 
                         (list -130.02 -190.661) 
                         (list -130.037 -190.695) 
                         (list -130.054 -190.729) 
                         (list -130.073 -190.762) 
                         (list -130.092 -190.794) 
                         (list -130.113 -190.826) 
                         (list -130.135 -190.857) 
                         (list -130.158 -190.887) 
                         (list -130.182 -190.917) 
                         (list -130.207 -190.945) 
                         (list -130.233 -190.973) 
                         (list -130.26 -191.0) 
                         (list -130.287 -191.026) 
                         (list -130.316 -191.051) 
                         (list -130.345 -191.075) 
                         (list -130.375 -191.098) 
                         (list -130.419 -191.129) 
                         (list -130.463 -191.158) 
                         (list -130.509 -191.186) 
                         (list -130.555 -191.212) 
                         (list -130.602 -191.237) 
                         (list -130.651 -191.26) 
                         (list -130.699 -191.282) 
                         (list -130.749 -191.302) 
                         (list -130.799 -191.32) 
                         (list -130.85 -191.336) 
                         (list -130.901 -191.351) 
                         (list -130.953 -191.364) 
                         (list -131.005 -191.375) 
                         (list -130.973 -191.397) 
                         (list -130.942 -191.419) 
                         (list -130.911 -191.442) 
                         (list -130.882 -191.467) 
                         (list -130.853 -191.492) 
                         (list -130.825 -191.518) 
                         (list -130.798 -191.545) 
                         (list -130.772 -191.573) 
                         (list -130.747 -191.602) 
                         (list -130.723 -191.632) 
                         (list -130.699 -191.662) 
                         (list -130.525 -191.552) 
                         (list -130.354 -191.437) 
                         (list -130.187 -191.316) 
                         (list -130.024 -191.19) 
                         (list -130.005 -191.175) 
                         (list -129.987 -191.159) 
                         (list -129.969 -191.142) 
                         (list -129.952 -191.125) 
                         (list -129.936 -191.107) 
                         (list -129.92 -191.089) 
                         (list -129.905 -191.07) 
                         (list -129.89 -191.051) 
                         (list -129.876 -191.031) 
                         (list -129.863 -191.01) 
                         (list -129.85 -190.99) 
                         (list -129.838 -190.968) 
                         (list -129.748 -190.794) 
                         (list -129.663 -190.617) 
                         (list -129.607 -190.626) 
                         (list -129.571 -190.702) 
                         (list -129.532 -190.777) 
                         (list -129.49 -190.85) 
                         (list -129.446 -190.922) 
                         (list -129.4 -190.992) 
                         (list -129.351 -191.06) 
                         (list -129.3 -191.127) 
                         (list -129.246 -191.192) 
                         (list -129.19 -191.255) 
                         (list -129.157 -191.29) 
                         (list -129.123 -191.324) 
                         (list -129.087 -191.357) 
                         (list -129.051 -191.388) 
                         (list -129.013 -191.419) 
                         (list -128.974 -191.447) 
                         (list -128.935 -191.475) 
                         (list -128.894 -191.501) 
                         (list -128.853 -191.526) 
                         (list -128.811 -191.549) 
                         (list -128.767 -191.571) 
                         (list -128.724 -191.592) 
                         (list -128.679 -191.611) 
                         (list -128.634 -191.628) 
                         (list -128.589 -191.644) 
                         (list -128.557 -191.592) 
                         (list -128.523 -191.542) 
                         (list -128.487 -191.493) 
                         (list -128.45 -191.446) 
                         (list -128.412 -191.399) 
                         (list -128.371 -191.354) 
                         (list -128.329 -191.311) 
                         (list -128.39 -191.29) 
                         (list -128.45 -191.268) 
                         (list -128.509 -191.244) 
                         (list -128.567 -191.218) 
                         (list -128.625 -191.19) 
                         (list -128.681 -191.16) 
                         (list -128.737 -191.128) 
                         (list -128.791 -191.094) 
                         (list -128.844 -191.059) 
                         (list -128.896 -191.022) 
                         (list -128.947 -190.983) 
                         (list -128.996 -190.943) 
                         (list -129.045 -190.901) 
                         (list -129.091 -190.857) 
                         (list -129.136 -190.812) 
                         (list -129.18 -190.765) 
                         (list -129.222 -190.717) 
                         (list -129.263 -190.668) 
                         (list -129.301 -190.617) 
                         (list -128.45 -190.626) 
                         (list -128.45 -190.349) 
                         (list -129.598 -190.358) 
                         (list -129.57 -189.969) 
                         (list -128.663 -189.96) 
                         (list -128.663 -188.591) 
                         (list -129.144 -188.582) 
                         (list -129.144 -188.156) 
                         (list -128.468 -188.175) 
                         (list -128.487 -187.897) 
                         (list -129.135 -187.916) 
                         (list -129.116 -187.463) 
                         (list -129.45 -187.453) 
                         (list -129.422 -187.925) 
                         (list -129.428 -188.163) 
                         (list -129.428 -188.573) 
                         "c"
         )
        (command "pline" (list -112.472 -191.886) "w" 0 0 
                         (list -112.473 -191.894) 
                         (list -112.474 -191.903) 
                         (list -112.473 -191.911) 
                         (list -112.472 -191.919) 
                         (list -112.47 -191.927) 
                         (list -112.467 -191.935) 
                         (list -112.464 -191.943) 
                         (list -112.459 -191.95) 
                         (list -112.454 -191.957) 
                         (list -112.448 -191.963) 
                         (list -112.441 -191.969) 
                         (list -112.433 -191.975) 
                         (list -112.425 -191.98) 
                         (list -112.415 -191.984) 
                         (list -112.405 -191.988) 
                         (list -112.413 -192.012) 
                         (list -112.237 -191.998) 
                         (list -112.237 -191.973) 
                         (list -112.227 -191.973) 
                         (list -112.217 -191.971) 
                         (list -112.207 -191.969) 
                         (list -112.199 -191.966) 
                         (list -112.19 -191.963) 
                         (list -112.183 -191.958) 
                         (list -112.176 -191.953) 
                         (list -112.169 -191.948) 
                         (list -112.164 -191.942) 
                         (list -112.159 -191.936) 
                         (list -112.154 -191.929) 
                         (list -112.151 -191.922) 
                         (list -112.148 -191.915) 
                         (list -112.146 -191.908) 
                         (list -112.145 -191.9) 
                         (list -112.144 -191.893) 
                         (list -112.144 -191.47) 
                         (list -112.144 -191.46) 
                         (list -112.144 -191.45) 
                         (list -112.143 -191.44) 
                         (list -112.142 -191.431) 
                         (list -112.142 -191.421) 
                         (list -112.141 -191.413) 
                         (list -112.139 -191.404) 
                         (list -112.138 -191.395) 
                         (list -112.135 -191.379) 
                         (list -112.13 -191.363) 
                         (list -112.126 -191.348) 
                         (list -112.12 -191.335) 
                         (list -112.114 -191.321) 
                         (list -112.108 -191.309) 
                         (list -112.1 -191.297) 
                         (list -112.093 -191.287) 
                         (list -112.084 -191.276) 
                         (list -112.076 -191.267) 
                         (list -112.066 -191.258) 
                         (list -112.056 -191.25) 
                         (list -112.046 -191.242) 
                         (list -112.035 -191.235) 
                         (list -112.024 -191.229) 
                         (list -112.012 -191.223) 
                         (list -112.001 -191.218) 
                         (list -111.988 -191.214) 
                         (list -111.976 -191.209) 
                         (list -111.963 -191.206) 
                         (list -111.949 -191.203) 
                         (list -111.936 -191.2) 
                         (list -111.922 -191.198) 
                         (list -111.908 -191.197) 
                         (list -111.894 -191.195) 
                         (list -111.879 -191.194) 
                         (list -111.865 -191.194) 
                         (list -111.85 -191.194) 
                         (list -111.836 -191.194) 
                         (list -111.822 -191.195) 
                         (list -111.808 -191.196) 
                         (list -111.794 -191.198) 
                         (list -111.78 -191.2) 
                         (list -111.766 -191.203) 
                         (list -111.753 -191.206) 
                         (list -111.739 -191.21) 
                         (list -111.726 -191.214) 
                         (list -111.713 -191.219) 
                         (list -111.7 -191.224) 
                         (list -111.688 -191.229) 
                         (list -111.676 -191.235) 
                         (list -111.664 -191.242) 
                         (list -111.653 -191.249) 
                         (list -111.642 -191.256) 
                         (list -111.631 -191.263) 
                         (list -111.621 -191.271) 
                         (list -111.612 -191.28) 
                         (list -111.603 -191.288) 
                         (list -111.594 -191.298) 
                         (list -111.586 -191.307) 
                         (list -111.579 -191.317) 
                         (list -111.572 -191.327) 
                         (list -111.566 -191.337) 
                         (list -111.561 -191.348) 
                         (list -111.556 -191.359) 
                         (list -111.553 -191.37) 
                         (list -111.55 -191.382) 
                         (list -111.548 -191.394) 
                         (list -111.546 -191.406) 
                         (list -111.546 -191.418) 
                         (list -111.546 -191.879) 
                         (list -111.546 -191.886) 
                         (list -111.545 -191.893) 
                         (list -111.544 -191.901) 
                         (list -111.543 -191.908) 
                         (list -111.54 -191.916) 
                         (list -111.537 -191.924) 
                         (list -111.533 -191.932) 
                         (list -111.529 -191.939) 
                         (list -111.523 -191.946) 
                         (list -111.517 -191.952) 
                         (list -111.509 -191.958) 
                         (list -111.5 -191.964) 
                         (list -111.49 -191.968) 
                         (list -111.479 -191.971) 
                         (list -111.472 -191.972) 
                         (list -111.466 -191.973) 
                         (list -111.459 -191.973) 
                         (list -111.451 -191.973) 
                         (list -111.451 -191.998) 
                         (list -111.183 -191.915) 
                         (list -111.284 -191.647) 
                         (list -111.248 -191.634) 
                         (list -111.236 -191.651) 
                         (list -111.222 -191.667) 
                         (list -111.208 -191.683) 
                         (list -111.193 -191.699) 
                         (list -111.178 -191.715) 
                         (list -111.161 -191.73) 
                         (list -111.144 -191.743) 
                         (list -111.126 -191.756) 
                         (list -111.107 -191.767) 
                         (list -111.088 -191.775) 
                         (list -111.067 -191.782) 
                         (list -111.046 -191.787) 
                         (list -111.024 -191.789) 
                         (list -111.002 -191.788) 
                         (list -110.991 -191.787) 
                         (list -110.979 -191.784) 
                         (list -110.967 -191.781) 
                         (list -110.955 -191.777) 
                         (list -110.945 -191.773) 
                         (list -110.934 -191.769) 
                         (list -110.924 -191.763) 
                         (list -110.913 -191.756) 
                         (list -110.902 -191.748) 
                         (list -110.892 -191.74) 
                         (list -110.882 -191.731) 
                         (list -110.873 -191.721) 
                         (list -110.865 -191.71) 
                         (list -110.858 -191.698) 
                         (list -110.852 -191.686) 
                         (list -110.848 -191.673) 
                         (list -110.846 -191.659) 
                         (list -110.846 -191.645) 
                         (list -110.848 -191.63) 
                         (list -110.852 -191.614) 
                         (list -110.858 -191.601) 
                         (list -110.866 -191.589) 
                         (list -110.875 -191.578) 
                         (list -110.885 -191.569) 
                         (list -110.895 -191.561) 
                         (list -110.907 -191.554) 
                         (list -110.918 -191.549) 
                         (list -110.931 -191.544) 
                         (list -110.943 -191.54) 
                         (list -110.954 -191.537) 
                         (list -110.966 -191.534) 
                         (list -110.977 -191.532) 
                         (list -110.986 -191.531) 
                         (list -110.995 -191.53) 
                         (list -111.003 -191.529) 
                         (list -111.008 -191.529) 
                         (list -111.121 -191.521) 
                         (list -111.144 -191.519) 
                         (list -111.168 -191.515) 
                         (list -111.191 -191.509) 
                         (list -111.213 -191.502) 
                         (list -111.235 -191.493) 
                         (list -111.255 -191.484) 
                         (list -111.275 -191.473) 
                         (list -111.294 -191.461) 
                         (list -111.312 -191.448) 
                         (list -111.328 -191.434) 
                         (list -111.343 -191.42) 
                         (list -111.357 -191.404) 
                         (list -111.369 -191.388) 
                         (list -111.38 -191.372) 
                         (list -111.389 -191.355) 
                         (list -111.396 -191.338) 
                         (list -111.402 -191.319) 
                         (list -111.405 -191.299) 
                         (list -111.406 -191.278) 
                         (list -111.405 -191.256) 
                         (list -111.401 -191.233) 
                         (list -111.396 -191.21) 
                         (list -111.388 -191.188) 
                         (list -111.378 -191.166) 
                         (list -111.366 -191.144) 
                         (list -111.353 -191.123) 
                         (list -111.337 -191.103) 
                         (list -111.319 -191.085) 
                         (list -111.299 -191.068) 
                         (list -111.278 -191.052) 
                         (list -111.266 -191.046) 
                         (list -111.255 -191.039) 
                         (list -111.242 -191.034) 
                         (list -111.229 -191.029) 
                         (list -111.209 -191.021) 
                         (list -111.189 -191.015) 
                         (list -111.171 -191.011) 
                         (list -111.153 -191.007) 
                         (list -111.137 -191.003) 
                         (list -111.122 -191.001) 
                         (list -111.108 -190.999) 
                         (list -111.095 -190.998) 
                         (list -111.083 -190.997) 
                         (list -111.072 -190.996) 
                         (list -111.062 -190.996) 
                         (list -111.052 -190.995) 
                         (list -111.036 -190.993) 
                         (list -111.024 -190.99) 
                         (list -111.015 -190.986) 
                         (list -111.009 -190.981) 
                         (list -111.005 -190.975) 
                         (list -111.002 -190.969) 
                         (list -111.0 -190.956) 
                         (list -111.001 -190.945) 
                         (list -110.971 -190.935) 
                         (list -111.293 -190.614) 
                         (list -111.325 -190.634) 
                         (list -111.358 -190.654) 
                         (list -111.391 -190.672) 
                         (list -111.425 -190.689) 
                         (list -111.46 -190.705) 
                         (list -111.495 -190.719) 
                         (list -111.53 -190.733) 
                         (list -111.567 -190.745) 
                         (list -111.603 -190.756) 
                         (list -111.64 -190.765) 
                         (list -111.677 -190.774) 
                         (list -111.714 -190.781) 
                         (list -111.752 -190.787) 
                         (list -111.79 -190.791) 
                         (list -111.828 -190.794) 
                         (list -111.866 -190.796) 
                         (list -111.904 -190.797) 
                         (list -111.942 -190.796) 
                         (list -111.98 -190.794) 
                         (list -112.018 -190.79) 
                         (list -112.056 -190.785) 
                         (list -112.093 -190.779) 
                         (list -112.131 -190.772) 
                         (list -112.168 -190.763) 
                         (list -112.205 -190.753) 
                         (list -112.241 -190.742) 
                         (list -112.277 -190.73) 
                         (list -112.313 -190.716) 
                         (list -112.348 -190.701) 
                         (list -112.382 -190.685) 
                         (list -112.416 -190.667) 
                         (list -112.449 -190.649) 
                         (list -112.482 -190.629) 
                         (list -112.514 -190.609) 
                         (list -112.545 -190.587) 
                         (list -112.576 -190.564) 
                         (list -112.605 -190.54) 
                         (list -112.634 -190.515) 
                         (list -112.662 -190.489) 
                         (list -112.689 -190.462) 
                         (list -112.715 -190.434) 
                         (list -112.74 -190.405) 
                         (list -112.764 -190.376) 
                         (list -112.787 -190.345) 
                         (list -112.809 -190.314) 
                         (list -112.829 -190.282) 
                         (list -112.849 -190.25) 
                         (list -112.868 -190.217) 
                         (list -112.885 -190.183) 
                         (list -112.901 -190.148) 
                         (list -112.916 -190.113) 
                         (list -112.93 -190.078) 
                         (list -112.943 -190.042) 
                         (list -112.954 -190.005) 
                         (list -112.964 -189.969) 
                         (list -112.973 -189.932) 
                         (list -112.98 -189.894) 
                         (list -112.986 -189.857) 
                         (list -112.991 -189.819) 
                         (list -112.995 -189.781) 
                         (list -112.997 -189.743) 
                         (list -112.998 -189.705) 
                         (list -112.997 -189.667) 
                         (list -112.995 -189.629) 
                         (list -112.992 -189.591) 
                         (list -112.988 -189.553) 
                         (list -112.982 -189.515) 
                         (list -112.975 -189.478) 
                         (list -112.967 -189.441) 
                         (list -112.957 -189.404) 
                         (list -112.946 -189.367) 
                         (list -112.934 -189.331) 
                         (list -112.921 -189.295) 
                         (list -112.906 -189.26) 
                         (list -112.891 -189.226) 
                         (list -112.874 -189.192) 
                         (list -112.855 -189.158) 
                         (list -112.836 -189.125) 
                         (list -112.816 -189.093) 
                         (list -112.794 -189.062) 
                         (list -112.772 -189.031) 
                         (list -112.748 -189.001) 
                         (list -112.723 -188.972) 
                         (list -112.697 -188.944) 
                         (list -112.671 -188.917) 
                         (list -112.643 -188.891) 
                         (list -112.615 -188.865) 
                         (list -112.585 -188.841) 
                         (list -112.555 -188.818) 
                         (list -112.524 -188.795) 
                         (list -112.493 -188.774) 
                         (list -112.46 -188.754) 
                         (list -112.427 -188.735) 
                         (list -112.394 -188.718) 
                         (list -112.359 -188.701) 
                         (list -112.324 -188.686) 
                         (list -112.289 -188.672) 
                         (list -112.253 -188.659) 
                         (list -112.217 -188.647) 
                         (list -112.18 -188.637) 
                         (list -112.143 -188.628) 
                         (list -112.106 -188.62) 
                         (list -112.068 -188.613) 
                         (list -112.031 -188.608) 
                         (list -111.993 -188.604) 
                         (list -111.955 -188.602) 
                         (list -111.917 -188.6) 
                         (list -111.879 -188.601) 
                         (list -111.841 -188.602) 
                         (list -111.803 -188.605) 
                         (list -111.765 -188.609) 
                         (list -111.727 -188.614) 
                         (list -111.69 -188.621) 
                         (list -111.652 -188.629) 
                         (list -111.615 -188.638) 
                         (list -111.579 -188.648) 
                         (list -111.542 -188.66) 
                         (list -111.507 -188.673) 
                         (list -111.471 -188.687) 
                         (list -111.437 -188.703) 
                         (list -111.402 -188.719) 
                         (list -111.369 -188.737) 
                         (list -111.336 -188.756) 
                         (list -111.303 -188.776) 
                         (list -111.257 -188.514) 
                         (list -111.085 -188.544) 
                         (list -111.052 -188.356) 
                         (list -110.868 -188.388) 
                         (list -110.835 -188.196) 
                         (list -110.655 -188.228) 
                         (list -110.625 -188.057) 
                         (list -110.441 -188.089) 
                         (list -110.407 -187.897) 
                         (list -110.245 -187.926) 
                         (list -110.21 -187.725) 
                         (list -109.966 -187.768) 
                         (list -110.034 -187.701) 
                         (list -110.104 -187.638) 
                         (list -110.176 -187.576) 
                         (list -110.25 -187.517) 
                         (list -110.326 -187.461) 
                         (list -110.405 -187.407) 
                         (list -110.485 -187.356) 
                         (list -110.566 -187.308) 
                         (list -110.65 -187.263) 
                         (list -110.735 -187.221) 
                         (list -110.821 -187.182) 
                         (list -110.909 -187.145) 
                         (list -110.998 -187.112) 
                         (list -111.088 -187.082) 
                         (list -111.179 -187.055) 
                         (list -111.27 -187.032) 
                         (list -111.363 -187.011) 
                         (list -111.456 -186.994) 
                         (list -111.55 -186.98) 
                         (list -111.644 -186.969) 
                         (list -111.739 -186.962) 
                         (list -111.834 -186.958) 
                         (list -111.929 -186.957) 
                         (list -112.023 -186.959) 
                         (list -112.118 -186.965) 
                         (list -112.212 -186.974) 
                         (list -112.306 -186.987) 
                         (list -112.4 -187.002) 
                         (list -112.493 -187.021) 
                         (list -112.585 -187.043) 
                         (list -112.677 -187.069) 
                         (list -112.767 -187.097) 
                         (list -112.856 -187.129) 
                         (list -112.945 -187.163) 
                         (list -113.032 -187.201) 
                         (list -113.117 -187.242) 
                         (list -113.202 -187.286) 
                         (list -113.284 -187.332) 
                         (list -113.365 -187.382) 
                         (list -113.444 -187.434) 
                         (list -113.521 -187.489) 
                         (list -113.597 -187.547) 
                         (list -113.67 -187.607) 
                         (list -113.741 -187.67) 
                         (list -113.81 -187.735) 
                         (list -113.876 -187.803) 
                         (list -113.941 -187.873) 
                         (list -114.002 -187.945) 
                         (list -114.061 -188.019) 
                         (list -114.118 -188.095) 
                         (list -114.172 -188.173) 
                         (list -114.223 -188.253) 
                         (list -114.271 -188.335) 
                         (list -114.317 -188.418) 
                         (list -114.359 -188.503) 
                         (list -114.399 -188.589) 
                         (list -114.435 -188.676) 
                         (list -114.468 -188.765) 
                         (list -114.499 -188.855) 
                         (list -114.526 -188.946) 
                         (list -114.55 -189.038) 
                         (list -114.57 -189.13) 
                         (list -114.588 -189.224) 
                         (list -114.602 -189.317) 
                         (list -114.613 -189.412) 
                         (list -114.621 -189.506) 
                         (list -114.625 -189.601) 
                         (list -114.626 -189.696) 
                         (list -114.624 -189.791) 
                         (list -114.618 -189.885) 
                         (list -114.61 -189.98) 
                         (list -114.597 -190.074) 
                         (list -114.582 -190.167) 
                         (list -114.563 -190.26) 
                         (list -114.541 -190.353) 
                         (list -114.516 -190.444) 
                         (list -114.488 -190.535) 
                         (list -114.457 -190.624) 
                         (list -114.422 -190.712) 
                         (list -114.385 -190.8) 
                         (list -114.344 -190.885) 
                         (list -114.301 -190.97) 
                         (list -114.254 -191.052) 
                         (list -114.205 -191.133) 
                         (list -114.153 -191.213) 
                         (list -114.098 -191.29) 
                         (list -114.041 -191.365) 
                         (list -113.981 -191.439) 
                         (list -113.918 -191.51) 
                         (list -113.853 -191.579) 
                         (list -113.785 -191.646) 
                         (list -113.716 -191.71) 
                         (list -113.644 -191.772) 
                         (list -113.57 -191.831) 
                         (list -113.494 -191.888) 
                         (list -113.416 -191.942) 
                         (list -113.336 -191.994) 
                         (list -113.255 -192.042) 
                         (list -113.172 -192.088) 
                         (list -113.087 -192.13) 
                         (list -113.001 -192.17) 
                         (list -112.913 -192.207) 
                         (list -112.825 -192.24) 
                         (list -112.735 -192.271) 
                         (list -112.644 -192.298) 
                         (list -112.552 -192.322) 
                         (list -112.46 -192.343) 
                         (list -112.367 -192.361) 
                         (list -112.273 -192.376) 
                         (list -112.179 -192.387) 
                         (list -112.084 -192.395) 
                         (list -111.989 -192.399) 
                         (list -111.895 -192.401) 
                         (list -111.8 -192.399) 
                         (list -111.705 -192.393) 
                         (list -111.611 -192.385) 
                         (list -111.516 -192.373) 
                         (list -111.423 -192.358) 
                         (list -111.33 -192.339) 
                         (list -111.237 -192.318) 
                         (list -111.146 -192.293) 
                         (list -111.055 -192.265) 
                         (list -110.966 -192.234) 
                         (list -110.877 -192.199) 
                         (list -110.79 -192.162) 
                         (list -110.704 -192.122) 
                         (list -110.62 -192.079) 
                         (list -110.537 -192.032) 
                         (list -110.456 -191.983) 
                         (list -110.376 -191.931) 
                         (list -110.299 -191.877) 
                         (list -110.223 -191.82) 
                         (list -110.15 -191.76) 
                         (list -110.883 -191.172) 
                         (list -110.921 -191.186) 
                         (list -110.929 -191.175) 
                         (list -110.938 -191.164) 
                         (list -110.947 -191.154) 
                         (list -110.955 -191.144) 
                         (list -110.964 -191.135) 
                         (list -110.973 -191.127) 
                         (list -110.981 -191.119) 
                         (list -110.99 -191.111) 
                         (list -111.007 -191.098) 
                         (list -111.024 -191.087) 
                         (list -111.04 -191.078) 
                         (list -111.057 -191.071) 
                         (list -111.073 -191.065) 
                         (list -111.09 -191.062) 
                         (list -111.106 -191.06) 
                         (list -111.123 -191.059) 
                         (list -111.139 -191.06) 
                         (list -111.156 -191.063) 
                         (list -111.172 -191.067) 
                         (list -111.189 -191.072) 
                         (list -111.201 -191.077) 
                         (list -111.211 -191.082) 
                         (list -111.221 -191.088) 
                         (list -111.23 -191.094) 
                         (list -111.246 -191.109) 
                         (list -111.258 -191.125) 
                         (list -111.266 -191.143) 
                         (list -111.27 -191.161) 
                         (list -111.271 -191.171) 
                         (list -111.27 -191.181) 
                         (list -111.268 -191.19) 
                         (list -111.265 -191.2) 
                         (list -111.261 -191.211) 
                         (list -111.255 -191.222) 
                         (list -111.249 -191.231) 
                         (list -111.242 -191.24) 
                         (list -111.226 -191.254) 
                         (list -111.208 -191.265) 
                         (list -111.197 -191.27) 
                         (list -111.186 -191.274) 
                         (list -111.175 -191.278) 
                         (list -111.162 -191.281) 
                         (list -111.149 -191.283) 
                         (list -111.136 -191.285) 
                         (list -111.122 -191.287) 
                         (list -111.107 -191.289) 
                         (list -110.97 -191.3) 
                         (list -110.949 -191.303) 
                         (list -110.928 -191.307) 
                         (list -110.908 -191.312) 
                         (list -110.889 -191.318) 
                         (list -110.87 -191.325) 
                         (list -110.853 -191.334) 
                         (list -110.837 -191.344) 
                         (list -110.821 -191.355) 
                         (list -110.807 -191.368) 
                         (list -110.793 -191.381) 
                         (list -110.781 -191.396) 
                         (list -110.769 -191.412) 
                         (list -110.758 -191.43) 
                         (list -110.748 -191.448) 
                         (list -110.739 -191.467) 
                         (list -110.73 -191.488) 
                         (list -110.725 -191.504) 
                         (list -110.721 -191.519) 
                         (list -110.718 -191.534) 
                         (list -110.715 -191.549) 
                         (list -110.714 -191.563) 
                         (list -110.713 -191.577) 
                         (list -110.714 -191.591) 
                         (list -110.714 -191.604) 
                         (list -110.716 -191.617) 
                         (list -110.719 -191.63) 
                         (list -110.722 -191.642) 
                         (list -110.726 -191.654) 
                         (list -110.736 -191.677) 
                         (list -110.749 -191.698) 
                         (list -110.763 -191.718) 
                         (list -110.78 -191.737) 
                         (list -110.797 -191.754) 
                         (list -110.817 -191.769) 
                         (list -110.837 -191.783) 
                         (list -110.859 -191.795) 
                         (list -110.881 -191.806) 
                         (list -110.904 -191.815) 
                         (list -110.922 -191.821) 
                         (list -110.939 -191.826) 
                         (list -110.956 -191.83) 
                         (list -110.972 -191.833) 
                         (list -110.987 -191.835) 
                         (list -111.001 -191.837) 
                         (list -111.015 -191.838) 
                         (list -111.028 -191.839) 
                         (list -111.041 -191.839) 
                         (list -111.053 -191.84) 
                         (list -111.065 -191.84) 
                         (list -111.076 -191.841) 
                         (list -111.096 -191.844) 
                         (list -111.115 -191.849) 
                         (list -111.125 -191.853) 
                         (list -111.133 -191.859) 
                         (list -111.14 -191.866) 
                         (list -111.145 -191.873) 
                         (list -111.149 -191.881) 
                         (list -111.151 -191.889) 
                         (list -111.152 -191.896) 
                         (list -111.15 -191.903) 
                         (list -111.183 -191.915) 
                         (list -111.451 -191.998) 
                         (list -111.825 -191.998) 
                         (list -111.825 -191.973) 
                         (list -111.811 -191.973) 
                         (list -111.798 -191.971) 
                         (list -111.787 -191.968) 
                         (list -111.777 -191.964) 
                         (list -111.768 -191.958) 
                         (list -111.76 -191.953) 
                         (list -111.754 -191.946) 
                         (list -111.748 -191.94) 
                         (list -111.743 -191.932) 
                         (list -111.739 -191.925) 
                         (list -111.736 -191.917) 
                         (list -111.734 -191.91) 
                         (list -111.732 -191.902) 
                         (list -111.731 -191.895) 
                         (list -111.73 -191.889) 
                         (list -111.73 -191.883) 
                         (list -111.73 -191.442) 
                         (list -111.73 -191.43) 
                         (list -111.731 -191.417) 
                         (list -111.732 -191.402) 
                         (list -111.734 -191.387) 
                         (list -111.736 -191.379) 
                         (list -111.738 -191.371) 
                         (list -111.74 -191.362) 
                         (list -111.742 -191.354) 
                         (list -111.748 -191.338) 
                         (list -111.756 -191.322) 
                         (list -111.76 -191.314) 
                         (list -111.765 -191.307) 
                         (list -111.771 -191.299) 
                         (list -111.777 -191.292) 
                         (list -111.784 -191.286) 
                         (list -111.791 -191.279) 
                         (list -111.799 -191.274) 
                         (list -111.808 -191.268) 
                         (list -111.817 -191.263) 
                         (list -111.827 -191.259) 
                         (list -111.837 -191.255) 
                         (list -111.849 -191.252) 
                         (list -111.861 -191.249) 
                         (list -111.874 -191.247) 
                         (list -111.888 -191.246) 
                         (list -111.903 -191.246) 
                         (list -111.917 -191.246) 
                         (list -111.93 -191.247) 
                         (list -111.942 -191.248) 
                         (list -111.954 -191.25) 
                         (list -111.965 -191.253) 
                         (list -111.976 -191.256) 
                         (list -111.986 -191.26) 
                         (list -111.996 -191.264) 
                         (list -112.005 -191.268) 
                         (list -112.014 -191.273) 
                         (list -112.022 -191.279) 
                         (list -112.03 -191.285) 
                         (list -112.037 -191.291) 
                         (list -112.044 -191.298) 
                         (list -112.05 -191.305) 
                         (list -112.056 -191.313) 
                         (list -112.062 -191.321) 
                         (list -112.067 -191.329) 
                         (list -112.071 -191.337) 
                         (list -112.076 -191.346) 
                         (list -112.08 -191.356) 
                         (list -112.083 -191.365) 
                         (list -112.086 -191.375) 
                         (list -112.089 -191.385) 
                         (list -112.091 -191.395) 
                         (list -112.093 -191.405) 
                         (list -112.095 -191.416) 
                         (list -112.096 -191.427) 
                         (list -112.098 -191.438) 
                         (list -112.098 -191.449) 
                         (list -112.099 -191.461) 
                         (list -112.099 -191.472) 
                         (list -112.099 -191.889) 
                         (list -112.098 -191.897) 
                         (list -112.097 -191.905) 
                         (list -112.095 -191.913) 
                         (list -112.093 -191.921) 
                         (list -112.089 -191.928) 
                         (list -112.085 -191.935) 
                         (list -112.08 -191.942) 
                         (list -112.075 -191.948) 
                         (list -112.069 -191.953) 
                         (list -112.062 -191.958) 
                         (list -112.054 -191.963) 
                         (list -112.046 -191.966) 
                         (list -112.037 -191.969) 
                         (list -112.028 -191.971) 
                         (list -112.017 -191.973) 
                         (list -112.007 -191.973) 
                         (list -112.007 -191.998) 
                         (list -112.237 -191.998) 
                         (list -112.413 -192.012) 
                         (list -112.791 -191.892) 
                         (list -112.801 -191.889) 
                         (list -112.81 -191.886) 
                         (list -112.82 -191.882) 
                         (list -112.83 -191.877) 
                         (list -112.84 -191.873) 
                         (list -112.849 -191.868) 
                         (list -112.859 -191.862) 
                         (list -112.869 -191.857) 
                         (list -112.879 -191.851) 
                         (list -112.888 -191.844) 
                         (list -112.898 -191.837) 
                         (list -112.906 -191.83) 
                         (list -112.915 -191.823) 
                         (list -112.924 -191.815) 
                         (list -112.932 -191.806) 
                         (list -112.94 -191.798) 
                         (list -112.947 -191.789) 
                         (list -112.954 -191.779) 
                         (list -112.96 -191.77) 
                         (list -112.965 -191.759) 
                         (list -112.971 -191.749) 
                         (list -112.975 -191.738) 
                         (list -112.979 -191.727) 
                         (list -112.982 -191.715) 
                         (list -112.984 -191.703) 
                         (list -112.986 -191.691) 
                         (list -112.986 -191.678) 
                         (list -112.986 -191.665) 
                         (list -112.985 -191.652) 
                         (list -112.983 -191.638) 
                         (list -112.98 -191.624) 
                         (list -112.976 -191.609) 
                         (list -112.972 -191.598) 
                         (list -112.967 -191.586) 
                         (list -112.962 -191.576) 
                         (list -112.956 -191.565) 
                         (list -112.95 -191.556) 
                         (list -112.943 -191.547) 
                         (list -112.936 -191.538) 
                         (list -112.928 -191.53) 
                         (list -112.92 -191.522) 
                         (list -112.912 -191.515) 
                         (list -112.903 -191.508) 
                         (list -112.894 -191.502) 
                         (list -112.884 -191.496) 
                         (list -112.874 -191.491) 
                         (list -112.864 -191.486) 
                         (list -112.854 -191.482) 
                         (list -112.843 -191.479) 
                         (list -112.832 -191.476) 
                         (list -112.821 -191.473) 
                         (list -112.809 -191.471) 
                         (list -112.798 -191.469) 
                         (list -112.786 -191.468) 
                         (list -112.775 -191.467) 
                         (list -112.763 -191.467) 
                         (list -112.75 -191.467) 
                         (list -112.739 -191.468) 
                         (list -112.726 -191.469) 
                         (list -112.714 -191.471) 
                         (list -112.702 -191.473) 
                         (list -112.69 -191.476) 
                         (list -112.678 -191.479) 
                         (list -112.666 -191.482) 
                         (list -112.55 -191.519) 
                         (list -112.478 -191.291) 
                         (list -112.476 -191.285) 
                         (list -112.475 -191.278) 
                         (list -112.474 -191.27) 
                         (list -112.473 -191.263) 
                         (list -112.473 -191.255) 
                         (list -112.474 -191.247) 
                         (list -112.475 -191.238) 
                         (list -112.478 -191.23) 
                         (list -112.481 -191.222) 
                         (list -112.486 -191.214) 
                         (list -112.491 -191.206) 
                         (list -112.498 -191.199) 
                         (list -112.506 -191.192) 
                         (list -112.516 -191.186) 
                         (list -112.527 -191.181) 
                         (list -112.54 -191.176) 
                         (list -112.534 -191.156) 
                         (list -112.58 -191.146) 
                         (list -112.596 -191.164) 
                         (list -112.605 -191.157) 
                         (list -112.615 -191.151) 
                         (list -112.624 -191.146) 
                         (list -112.634 -191.143) 
                         (list -112.643 -191.141) 
                         (list -112.652 -191.14) 
                         (list -112.662 -191.14) 
                         (list -112.67 -191.141) 
                         (list -112.679 -191.143) 
                         (list -112.687 -191.145) 
                         (list -112.694 -191.148) 
                         (list -112.702 -191.152) 
                         (list -112.709 -191.157) 
                         (list -112.715 -191.162) 
                         (list -112.721 -191.167) 
                         (list -112.726 -191.173) 
                         (list -113.084 -191.599) 
                         (list -113.089 -191.606) 
                         (list -113.093 -191.613) 
                         (list -113.097 -191.62) 
                         (list -113.1 -191.628) 
                         (list -113.102 -191.636) 
                         (list -113.104 -191.644) 
                         (list -113.105 -191.652) 
                         (list -113.104 -191.661) 
                         (list -113.103 -191.669) 
                         (list -113.101 -191.678) 
                         (list -113.098 -191.686) 
                         (list -113.094 -191.695) 
                         (list -113.089 -191.703) 
                         (list -113.083 -191.711) 
                         (list -113.076 -191.719) 
                         (list -113.068 -191.727) 
                         (list -113.084 -191.746) 
                         (list -113.583 -191.327) 
                         (list -113.43 -191.145) 
                         (list -113.412 -191.161) 
                         (list -113.419 -191.173) 
                         (list -113.426 -191.184) 
                         (list -113.432 -191.196) 
                         (list -113.437 -191.207) 
                         (list -113.442 -191.218) 
                         (list -113.446 -191.229) 
                         (list -113.449 -191.24) 
                         (list -113.452 -191.251) 
                         (list -113.454 -191.261) 
                         (list -113.456 -191.271) 
                         (list -113.457 -191.281) 
                         (list -113.457 -191.291) 
                         (list -113.457 -191.3) 
                         (list -113.457 -191.309) 
                         (list -113.456 -191.318) 
                         (list -113.455 -191.327) 
                         (list -113.453 -191.336) 
                         (list -113.45 -191.344) 
                         (list -113.448 -191.352) 
                         (list -113.445 -191.36) 
                         (list -113.438 -191.375) 
                         (list -113.43 -191.389) 
                         (list -113.421 -191.403) 
                         (list -113.412 -191.415) 
                         (list -113.401 -191.427) 
                         (list -113.39 -191.437) 
                         (list -113.309 -191.508) 
                         (list -113.303 -191.513) 
                         (list -113.298 -191.516) 
                         (list -113.292 -191.52) 
                         (list -113.287 -191.522) 
                         (list -113.278 -191.524) 
                         (list -113.269 -191.522) 
                         (list -113.26 -191.517) 
                         (list -113.251 -191.51) 
                         (list -113.246 -191.505) 
                         (list -113.241 -191.5) 
                         (list -113.236 -191.494) 
                         (list -113.231 -191.487) 
                         (list -113.062 -191.287) 
                         (list -113.073 -191.278) 
                         (list -113.082 -191.271) 
                         (list -113.092 -191.263) 
                         (list -113.102 -191.255) 
                         (list -113.113 -191.248) 
                         (list -113.124 -191.242) 
                         (list -113.137 -191.237) 
                         (list -113.15 -191.232) 
                         (list -113.165 -191.23) 
                         (list -113.172 -191.229) 
                         (list -113.18 -191.228) 
                         (list -113.187 -191.229) 
                         (list -113.196 -191.23) 
                         (list -113.204 -191.231) 
                         (list -113.213 -191.233) 
                         (list -113.222 -191.236) 
                         (list -113.231 -191.239) 
                         (list -113.24 -191.243) 
                         (list -113.25 -191.248) 
                         (list -113.26 -191.254) 
                         (list -113.27 -191.26) 
                         (list -113.281 -191.268) 
                         (list -113.292 -191.276) 
                         (list -113.303 -191.285) 
                         (list -113.315 -191.296) 
                         (list -113.335 -191.279) 
                         (list -113.089 -190.985) 
                         (list -113.068 -191.002) 
                         (list -113.077 -191.015) 
                         (list -113.084 -191.028) 
                         (list -113.09 -191.04) 
                         (list -113.095 -191.052) 
                         (list -113.1 -191.064) 
                         (list -113.104 -191.074) 
                         (list -113.107 -191.085) 
                         (list -113.109 -191.095) 
                         (list -113.111 -191.105) 
                         (list -113.112 -191.114) 
                         (list -113.113 -191.123) 
                         (list -113.113 -191.132) 
                         (list -113.112 -191.14) 
                         (list -113.111 -191.148) 
                         (list -113.11 -191.156) 
                         (list -113.108 -191.163) 
                         (list -113.103 -191.176) 
                         (list -113.096 -191.189) 
                         (list -113.089 -191.2) 
                         (list -113.081 -191.211) 
                         (list -113.072 -191.22) 
                         (list -113.063 -191.229) 
                         (list -113.054 -191.237) 
                         (list -113.045 -191.245) 
                         (list -113.034 -191.253) 
                         (list -112.864 -191.05) 
                         (list -112.857 -191.042) 
                         (list -112.851 -191.034) 
                         (list -112.846 -191.027) 
                         (list -112.842 -191.021) 
                         (list -112.839 -191.014) 
                         (list -112.837 -191.007) 
                         (list -112.836 -191.001) 
                         (list -112.836 -190.994) 
                         (list -112.838 -190.987) 
                         (list -112.842 -190.98) 
                         (list -112.847 -190.972) 
                         (list -112.853 -190.963) 
                         (list -112.858 -190.958) 
                         (list -112.862 -190.954) 
                         (list -112.867 -190.949) 
                         (list -112.872 -190.944) 
                         (list -112.878 -190.938) 
                         (list -112.885 -190.932) 
                         (list -112.891 -190.926) 
                         (list -112.899 -190.92) 
                         (list -112.908 -190.913) 
                         (list -112.917 -190.906) 
                         (list -112.925 -190.899) 
                         (list -112.934 -190.893) 
                         (list -112.944 -190.887) 
                         (list -112.953 -190.881) 
                         (list -112.962 -190.876) 
                         (list -112.971 -190.871) 
                         (list -112.981 -190.866) 
                         (list -112.991 -190.862) 
                         (list -113.001 -190.859) 
                         (list -113.011 -190.856) 
                         (list -113.021 -190.853) 
                         (list -113.032 -190.851) 
                         (list -113.042 -190.849) 
                         (list -113.053 -190.848) 
                         (list -113.067 -190.847) 
                         (list -113.08 -190.846) 
                         (list -113.093 -190.846) 
                         (list -113.105 -190.847) 
                         (list -113.118 -190.848) 
                         (list -113.129 -190.85) 
                         (list -113.141 -190.852) 
                         (list -113.153 -190.854) 
                         (list -113.165 -190.857) 
                         (list -113.176 -190.861) 
                         (list -113.188 -190.864) 
                         (list -113.201 -190.869) 
                         (list -113.213 -190.873) 
                         (list -113.226 -190.879) 
                         (list -113.239 -190.884) 
                         (list -113.253 -190.891) 
                         (list -113.277 -190.871) 
                         (list -113.086 -190.722) 
                         (list -113.109 -190.732) 
                         (list -113.131 -190.744) 
                         (list -113.137 -190.734) 
                         (list -113.144 -190.726) 
                         (list -113.151 -190.718) 
                         (list -113.159 -190.712) 
                         (list -113.166 -190.706) 
                         (list -113.175 -190.702) 
                         (list -113.183 -190.699) 
                         (list -113.191 -190.696) 
                         (list -113.2 -190.695) 
                         (list -113.208 -190.695) 
                         (list -113.217 -190.695) 
                         (list -113.225 -190.696) 
                         (list -113.233 -190.698) 
                         (list -113.241 -190.701) 
                         (list -113.249 -190.704) 
                         (list -113.257 -190.708) 
                         (list -113.741 -190.987) 
                         (list -113.747 -190.991) 
                         (list -113.753 -190.996) 
                         (list -113.758 -191.001) 
                         (list -113.763 -191.008) 
                         (list -113.767 -191.014) 
                         (list -113.771 -191.022) 
                         (list -113.774 -191.03) 
                         (list -113.777 -191.038) 
                         (list -113.779 -191.046) 
                         (list -113.78 -191.055) 
                         (list -113.78 -191.064) 
                         (list -113.779 -191.073) 
                         (list -113.777 -191.083) 
                         (list -113.775 -191.092) 
                         (list -113.771 -191.101) 
                         (list -113.766 -191.111) 
                         (list -113.788 -191.123) 
                         (list -113.978 -190.793) 
                         (list -113.983 -190.784) 
                         (list -113.989 -190.774) 
                         (list -113.994 -190.764) 
                         (list -113.999 -190.753) 
                         (list -114.004 -190.742) 
                         (list -114.008 -190.731) 
                         (list -114.013 -190.719) 
                         (list -114.017 -190.708) 
                         (list -114.021 -190.695) 
                         (list -114.025 -190.683) 
                         (list -114.028 -190.671) 
                         (list -114.031 -190.658) 
                         (list -114.033 -190.645) 
                         (list -114.035 -190.633) 
                         (list -114.037 -190.62) 
                         (list -114.038 -190.607) 
                         (list -114.038 -190.594) 
                         (list -114.038 -190.582) 
                         (list -114.037 -190.569) 
                         (list -114.035 -190.557) 
                         (list -114.033 -190.545) 
                         (list -114.03 -190.533) 
                         (list -114.026 -190.521) 
                         (list -114.021 -190.51) 
                         (list -114.016 -190.499) 
                         (list -114.01 -190.488) 
                         (list -114.002 -190.478) 
                         (list -113.994 -190.468) 
                         (list -113.985 -190.458) 
                         (list -113.975 -190.449) 
                         (list -113.963 -190.441) 
                         (list -113.951 -190.433) 
                         (list -113.941 -190.428) 
                         (list -113.931 -190.423) 
                         (list -113.921 -190.419) 
                         (list -113.912 -190.416) 
                         (list -113.902 -190.413) 
                         (list -113.892 -190.411) 
                         (list -113.883 -190.409) 
                         (list -113.874 -190.408) 
                         (list -113.865 -190.408) 
                         (list -113.856 -190.408) 
                         (list -113.847 -190.408) 
                         (list -113.838 -190.409) 
                         (list -113.829 -190.411) 
                         (list -113.82 -190.413) 
                         (list -113.812 -190.415) 
                         (list -113.804 -190.418) 
                         (list -113.788 -190.424) 
                         (list -113.772 -190.432) 
                         (list -113.757 -190.441) 
                         (list -113.742 -190.451) 
                         (list -113.729 -190.462) 
                         (list -113.715 -190.473) 
                         (list -113.703 -190.485) 
                         (list -113.691 -190.497) 
                         (list -113.518 -190.133) 
                         (list -113.515 -190.126) 
                         (list -113.512 -190.119) 
                         (list -113.511 -190.112) 
                         (list -113.51 -190.105) 
                         (list -113.51 -190.098) 
                         (list -113.511 -190.091) 
                         (list -113.513 -190.083) 
                         (list -113.517 -190.075) 
                         (list -113.496 -190.063) 
                         (list -113.533 -189.918) 
                         (list -113.533 -190.148) 
                         (list -113.558 -190.148) 
                         (list -113.559 -190.138) 
                         (list -113.56 -190.129) 
                         (list -113.562 -190.12) 
                         (list -113.565 -190.111) 
                         (list -113.568 -190.103) 
                         (list -113.572 -190.095) 
                         (list -113.577 -190.088) 
                         (list -113.582 -190.082) 
                         (list -113.588 -190.076) 
                         (list -113.595 -190.071) 
                         (list -113.602 -190.067) 
                         (list -113.61 -190.063) 
                         (list -113.618 -190.06) 
                         (list -113.626 -190.058) 
                         (list -113.635 -190.056) 
                         (list -113.644 -190.056) 
                         (list -114.209 -190.056) 
                         (list -114.219 -190.056) 
                         (list -114.228 -190.057) 
                         (list -114.237 -190.058) 
                         (list -114.245 -190.061) 
                         (list -114.252 -190.063) 
                         (list -114.259 -190.067) 
                         (list -114.265 -190.071) 
                         (list -114.27 -190.077) 
                         (list -114.275 -190.083) 
                         (list -114.28 -190.091) 
                         (list -114.283 -190.099) 
                         (list -114.287 -190.109) 
                         (list -114.289 -190.119) 
                         (list -114.291 -190.131) 
                         (list -114.292 -190.145) 
                         (list -114.292 -190.16) 
                         (list -114.317 -190.16) 
                         (list -114.317 -189.867) 
                         (list -113.781 -189.648) 
                         (list -114.317 -189.417) 
                         (list -114.317 -189.129) 
                         (list -114.292 -189.129) 
                         (list -114.291 -189.142) 
                         (list -114.289 -189.155) 
                         (list -114.287 -189.166) 
                         (list -114.283 -189.175) 
                         (list -114.278 -189.184) 
                         (list -114.272 -189.192) 
                         (list -114.266 -189.199) 
                         (list -114.259 -189.204) 
                         (list -114.252 -189.209) 
                         (list -114.245 -189.213) 
                         (list -114.237 -189.216) 
                         (list -114.229 -189.219) 
                         (list -114.222 -189.221) 
                         (list -114.214 -189.222) 
                         (list -114.207 -189.223) 
                         (list -114.2 -189.223) 
                         (list -113.649 -189.223) 
                         (list -113.643 -189.223) 
                         (list -113.636 -189.222) 
                         (list -113.629 -189.221) 
                         (list -113.621 -189.219) 
                         (list -113.614 -189.217) 
                         (list -113.606 -189.214) 
                         (list -113.599 -189.21) 
                         (list -113.592 -189.205) 
                         (list -113.585 -189.2) 
                         (list -113.579 -189.193) 
                         (list -113.573 -189.185) 
                         (list -113.568 -189.176) 
                         (list -113.564 -189.167) 
                         (list -113.561 -189.155) 
                         (list -113.559 -189.143) 
                         (list -113.558 -189.129) 
                         (list -113.533 -189.129) 
                         (list -113.517 -189.187) 
                         (list -113.512 -189.179) 
                         (list -113.508 -189.17) 
                         (list -113.505 -189.162) 
                         (list -113.504 -189.153) 
                         (list -113.503 -189.145) 
                         (list -113.503 -189.137) 
                         (list -113.505 -189.128) 
                         (list -113.507 -189.12) 
                         (list -113.509 -189.112) 
                         (list -113.512 -189.104) 
                         (list -113.516 -189.096) 
                         (list -113.52 -189.088) 
                         (list -113.53 -189.072) 
                         (list -113.539 -189.057) 
                         (list -113.928 -188.451) 
                         (list -113.907 -188.422) 
                         (list -113.177 -188.583) 
                         (list -113.169 -188.585) 
                         (list -113.161 -188.586) 
                         (list -113.153 -188.588) 
                         (list -113.146 -188.589) 
                         (list -113.132 -188.589) 
                         (list -113.119 -188.587) 
                         (list -113.113 -188.586) 
                         (list -113.106 -188.583) 
                         (list -113.101 -188.58) 
                         (list -113.095 -188.576) 
                         (list -113.089 -188.571) 
                         (list -113.083 -188.565) 
                         (list -113.077 -188.558) 
                         (list -113.071 -188.55) 
                         (list -113.121 -188.388) 
                         (list -113.102 -188.369) 
                         (list -113.088 -188.378) 
                         (list -113.075 -188.386) 
                         (list -113.061 -188.394) 
                         (list -113.048 -188.401) 
                         (list -113.035 -188.407) 
                         (list -113.022 -188.412) 
                         (list -113.009 -188.418) 
                         (list -112.997 -188.422) 
                         (list -112.985 -188.426) 
                         (list -112.972 -188.429) 
                         (list -112.96 -188.432) 
                         (list -112.949 -188.434) 
                         (list -112.937 -188.436) 
                         (list -112.926 -188.437) 
                         (list -112.915 -188.438) 
                         (list -112.904 -188.438) 
                         (list -112.894 -188.437) 
                         (list -112.884 -188.437) 
                         (list -112.874 -188.435) 
                         (list -112.864 -188.434) 
                         (list -112.855 -188.432) 
                         (list -112.845 -188.429) 
                         (list -112.837 -188.427) 
                         (list -112.828 -188.423) 
                         (list -112.82 -188.42) 
                         (list -112.812 -188.416) 
                         (list -112.804 -188.412) 
                         (list -112.797 -188.407) 
                         (list -112.79 -188.403) 
                         (list -112.784 -188.397) 
                         (list -112.778 -188.392) 
                         (list -112.772 -188.387) 
                         (list -112.76 -188.375) 
                         (list -112.75 -188.362) 
                         (list -112.74 -188.349) 
                         (list -112.732 -188.336) 
                         (list -112.726 -188.324) 
                         (list -112.721 -188.311) 
                         (list -112.717 -188.298) 
                         (list -112.714 -188.284) 
                         (list -112.713 -188.272) 
                         (list -112.714 -188.259) 
                         (list -112.716 -188.246) 
                         (list -112.72 -188.233) 
                         (list -112.726 -188.221) 
                         (list -112.733 -188.208) 
                         (list -112.737 -188.202) 
                         (list -112.742 -188.196) 
                         (list -112.747 -188.19) 
                         (list -112.753 -188.185) 
                         (list -112.764 -188.175) 
                         (list -112.775 -188.167) 
                         (list -112.786 -188.161) 
                         (list -112.798 -188.157) 
                         (list -112.81 -188.154) 
                         (list -112.822 -188.153) 
                         (list -112.835 -188.153) 
                         (list -112.847 -188.153) 
                         (list -112.859 -188.155) 
                         (list -112.871 -188.157) 
                         (list -112.883 -188.16) 
                         (list -112.895 -188.164) 
                         (list -112.907 -188.167) 
                         (list -112.919 -188.171) 
                         (list -112.93 -188.175) 
                         (list -112.941 -188.178) 
                         (list -113.07 -188.219) 
                         (list -113.084 -188.223) 
                         (list -113.099 -188.226) 
                         (list -113.115 -188.229) 
                         (list -113.132 -188.23) 
                         (list -113.149 -188.231) 
                         (list -113.166 -188.231) 
                         (list -113.183 -188.23) 
                         (list -113.201 -188.228) 
                         (list -113.218 -188.225) 
                         (list -113.235 -188.221) 
                         (list -113.251 -188.215) 
                         (list -113.268 -188.209) 
                         (list -113.283 -188.201) 
                         (list -113.298 -188.192) 
                         (list -113.312 -188.182) 
                         (list -113.324 -188.171) 
                         (list -113.332 -188.163) 
                         (list -113.34 -188.154) 
                         (list -113.347 -188.146) 
                         (list -113.353 -188.136) 
                         (list -113.36 -188.127) 
                         (list -113.366 -188.118) 
                         (list -113.371 -188.108) 
                         (list -113.377 -188.098) 
                         (list -113.381 -188.088) 
                         (list -113.385 -188.078) 
                         (list -113.389 -188.068) 
                         (list -113.392 -188.057) 
                         (list -113.395 -188.046) 
                         (list -113.398 -188.036) 
                         (list -113.399 -188.025) 
                         (list -113.4 -188.014) 
                         (list -113.401 -188.003) 
                         (list -113.401 -187.992) 
                         (list -113.4 -187.981) 
                         (list -113.399 -187.97) 
                         (list -113.397 -187.959) 
                         (list -113.395 -187.948) 
                         (list -113.392 -187.937) 
                         (list -113.388 -187.926) 
                         (list -113.384 -187.915) 
                         (list -113.379 -187.904) 
                         (list -113.373 -187.893) 
                         (list -113.366 -187.883) 
                         (list -113.359 -187.872) 
                         (list -113.351 -187.862) 
                         (list -113.342 -187.852) 
                         (list -113.333 -187.842) 
                         (list -113.321 -187.83) 
                         (list -113.308 -187.82) 
                         (list -113.296 -187.81) 
                         (list -113.283 -187.801) 
                         (list -113.271 -187.793) 
                         (list -113.259 -187.786) 
                         (list -113.247 -187.779) 
                         (list -113.235 -187.772) 
                         (list -113.224 -187.766) 
                         (list -113.213 -187.761) 
                         (list -113.203 -187.755) 
                         (list -113.193 -187.75) 
                         (list -113.184 -187.744) 
                         (list -113.175 -187.738) 
                         (list -113.168 -187.732) 
                         (list -113.161 -187.726) 
                         (list -113.157 -187.722) 
                         (list -113.155 -187.716) 
                         (list -113.155 -187.71) 
                         (list -113.156 -187.703) 
                         (list -113.157 -187.696) 
                         (list -113.16 -187.689) 
                         (list -113.163 -187.682) 
                         (list -113.166 -187.674) 
                         (list -113.148 -187.655) 
                         (list -112.775 -187.517) 
                         (list -112.415 -187.42) 
                         (list -112.408 -187.444) 
                         (list -112.419 -187.448) 
                         (list -112.429 -187.452) 
                         (list -112.437 -187.456) 
                         (list -112.445 -187.462) 
                         (list -112.452 -187.468) 
                         (list -112.459 -187.474) 
                         (list -112.464 -187.481) 
                         (list -112.469 -187.488) 
                         (list -112.473 -187.496) 
                         (list -112.476 -187.503) 
                         (list -112.478 -187.512) 
                         (list -112.48 -187.52) 
                         (list -112.48 -187.528) 
                         (list -112.48 -187.536) 
                         (list -112.479 -187.545) 
                         (list -112.477 -187.553) 
                         (list -112.408 -187.813) 
                         (list -112.233 -187.507) 
                         (list -112.223 -187.49) 
                         (list -112.215 -187.473) 
                         (list -112.211 -187.465) 
                         (list -112.209 -187.457) 
                         (list -112.209 -187.449) 
                         (list -112.21 -187.441) 
                         (list -112.212 -187.436) 
                         (list -112.215 -187.431) 
                         (list -112.218 -187.427) 
                         (list -112.223 -187.424) 
                         (list -112.234 -187.418) 
                         (list -112.247 -187.414) 
                         (list -112.262 -187.413) 
                         (list -112.277 -187.413) 
                         (list -112.293 -187.414) 
                         (list -112.308 -187.417) 
                         (list -112.315 -187.394) 
                         (list -111.993 -187.307) 
                         (list -111.986 -187.331) 
                         (list -112.0 -187.335) 
                         (list -112.014 -187.34) 
                         (list -112.027 -187.344) 
                         (list -112.039 -187.349) 
                         (list -112.05 -187.355) 
                         (list -112.061 -187.361) 
                         (list -112.072 -187.368) 
                         (list -112.082 -187.375) 
                         (list -112.092 -187.382) 
                         (list -112.101 -187.391) 
                         (list -112.11 -187.4) 
                         (list -112.119 -187.41) 
                         (list -112.128 -187.421) 
                         (list -112.136 -187.434) 
                         (list -112.145 -187.446) 
                         (list -112.153 -187.46) 
                         (list -112.281 -187.683) 
                         (list -111.842 -188.006) 
                         (list -111.835 -188.011) 
                         (list -111.827 -188.016) 
                         (list -111.818 -188.021) 
                         (list -111.808 -188.026) 
                         (list -111.797 -188.03) 
                         (list -111.786 -188.032) 
                         (list -111.774 -188.033) 
                         (list -111.762 -188.031) 
                         (list -111.756 -188.055) 
                         (list -112.134 -188.156) 
                         (list -112.141 -188.132) 
                         (list -112.131 -188.129) 
                         (list -112.122 -188.126) 
                         (list -112.113 -188.123) 
                         (list -112.105 -188.12) 
                         (list -112.098 -188.117) 
                         (list -112.092 -188.114) 
                         (list -112.086 -188.11) 
                         (list -112.081 -188.106) 
                         (list -112.074 -188.099) 
                         (list -112.069 -188.09) 
                         (list -112.067 -188.081) 
                         (list -112.068 -188.072) 
                         (list -112.071 -188.067) 
                         (list -112.075 -188.062) 
                         (list -112.08 -188.056) 
                         (list -112.087 -188.051) 
                         (list -112.101 -188.041) 
                         (list -112.113 -188.032) 
                         (list -112.369 -187.838) 
                         (list -112.391 -187.875) 
                         (list -112.333 -188.09) 
                         (list -112.331 -188.099) 
                         (list -112.327 -188.107) 
                         (list -112.323 -188.115) 
                         (list -112.318 -188.123) 
                         (list -112.313 -188.129) 
                         (list -112.307 -188.136) 
                         (list -112.301 -188.141) 
                         (list -112.294 -188.146) 
                         (list -112.286 -188.15) 
                         (list -112.278 -188.153) 
                         (list -112.269 -188.156) 
                         (list -112.26 -188.157) 
                         (list -112.25 -188.158) 
                         (list -112.24 -188.157) 
                         (list -112.23 -188.156) 
                         (list -112.219 -188.153) 
                         (list -112.212 -188.177) 
                         (list -112.573 -188.274) 
                         (list -112.579 -188.25) 
                         (list -112.566 -188.246) 
                         (list -112.555 -188.241) 
                         (list -112.545 -188.235) 
                         (list -112.536 -188.228) 
                         (list -112.529 -188.221) 
                         (list -112.523 -188.214) 
                         (list -112.518 -188.206) 
                         (list -112.514 -188.198) 
                         (list -112.512 -188.19) 
                         (list -112.51 -188.182) 
                         (list -112.509 -188.173) 
                         (list -112.508 -188.166) 
                         (list -112.508 -188.158) 
                         (list -112.509 -188.15) 
                         (list -112.51 -188.144) 
                         (list -112.512 -188.138) 
                         (list -112.655 -187.601) 
                         (list -112.658 -187.593) 
                         (list -112.661 -187.585) 
                         (list -112.665 -187.578) 
                         (list -112.67 -187.571) 
                         (list -112.675 -187.564) 
                         (list -112.681 -187.558) 
                         (list -112.688 -187.553) 
                         (list -112.695 -187.548) 
                         (list -112.703 -187.545) 
                         (list -112.711 -187.541) 
                         (list -112.72 -187.539) 
                         (list -112.729 -187.538) 
                         (list -112.738 -187.537) 
                         (list -112.748 -187.537) 
                         (list -112.758 -187.539) 
                         (list -112.769 -187.541) 
                         (list -112.775 -187.517) 
                         (list -113.148 -187.655) 
                         (list -112.968 -187.832) 
                         (list -112.985 -187.85) 
                         (list -112.995 -187.846) 
                         (list -113.005 -187.841) 
                         (list -113.015 -187.836) 
                         (list -113.025 -187.832) 
                         (list -113.035 -187.828) 
                         (list -113.045 -187.824) 
                         (list -113.065 -187.817) 
                         (list -113.076 -187.814) 
                         (list -113.086 -187.811) 
                         (list -113.096 -187.809) 
                         (list -113.106 -187.807) 
                         (list -113.116 -187.804) 
                         (list -113.126 -187.803) 
                         (list -113.137 -187.802) 
                         (list -113.147 -187.801) 
                         (list -113.157 -187.801) 
                         (list -113.167 -187.801) 
                         (list -113.177 -187.802) 
                         (list -113.187 -187.803) 
                         (list -113.197 -187.804) 
                         (list -113.207 -187.806) 
                         (list -113.216 -187.809) 
                         (list -113.226 -187.812) 
                         (list -113.235 -187.816) 
                         (list -113.245 -187.82) 
                         (list -113.254 -187.825) 
                         (list -113.263 -187.831) 
                         (list -113.272 -187.837) 
                         (list -113.281 -187.844) 
                         (list -113.29 -187.851) 
                         (list -113.299 -187.86) 
                         (list -113.307 -187.869) 
                         (list -113.314 -187.878) 
                         (list -113.321 -187.888) 
                         (list -113.326 -187.899) 
                         (list -113.33 -187.909) 
                         (list -113.333 -187.92) 
                         (list -113.335 -187.931) 
                         (list -113.336 -187.942) 
                         (list -113.335 -187.953) 
                         (list -113.334 -187.965) 
                         (list -113.331 -187.976) 
                         (list -113.327 -187.987) 
                         (list -113.321 -187.998) 
                         (list -113.315 -188.008) 
                         (list -113.307 -188.018) 
                         (list -113.298 -188.028) 
                         (list -113.288 -188.037) 
                         (list -113.279 -188.044) 
                         (list -113.269 -188.049) 
                         (list -113.258 -188.054) 
                         (list -113.247 -188.057) 
                         (list -113.236 -188.059) 
                         (list -113.224 -188.06) 
                         (list -113.212 -188.06) 
                         (list -113.2 -188.059) 
                         (list -113.188 -188.058) 
                         (list -113.175 -188.055) 
                         (list -113.162 -188.052) 
                         (list -113.149 -188.049) 
                         (list -113.135 -188.044) 
                         (list -113.122 -188.04) 
                         (list -113.108 -188.035) 
                         (list -113.006 -187.995) 
                         (list -112.998 -187.992) 
                         (list -112.987 -187.989) 
                         (list -112.981 -187.987) 
                         (list -112.975 -187.985) 
                         (list -112.968 -187.983) 
                         (list -112.96 -187.981) 
                         (list -112.952 -187.979) 
                         (list -112.944 -187.978) 
                         (list -112.935 -187.976) 
                         (list -112.927 -187.975) 
                         (list -112.917 -187.974) 
                         (list -112.908 -187.973) 
                         (list -112.898 -187.973) 
                         (list -112.888 -187.973) 
                         (list -112.877 -187.973) 
                         (list -112.867 -187.973) 
                         (list -112.856 -187.974) 
                         (list -112.846 -187.976) 
                         (list -112.835 -187.978) 
                         (list -112.824 -187.98) 
                         (list -112.813 -187.984) 
                         (list -112.802 -187.987) 
                         (list -112.791 -187.991) 
                         (list -112.78 -187.996) 
                         (list -112.769 -188.002) 
                         (list -112.758 -188.008) 
                         (list -112.747 -188.016) 
                         (list -112.737 -188.023) 
                         (list -112.726 -188.032) 
                         (list -112.716 -188.042) 
                         (list -112.708 -188.05) 
                         (list -112.701 -188.059) 
                         (list -112.694 -188.068) 
                         (list -112.687 -188.077) 
                         (list -112.681 -188.087) 
                         (list -112.675 -188.097) 
                         (list -112.67 -188.107) 
                         (list -112.666 -188.117) 
                         (list -112.661 -188.128) 
                         (list -112.658 -188.139) 
                         (list -112.655 -188.15) 
                         (list -112.652 -188.162) 
                         (list -112.65 -188.173) 
                         (list -112.649 -188.185) 
                         (list -112.648 -188.197) 
                         (list -112.648 -188.209) 
                         (list -112.649 -188.221) 
                         (list -112.65 -188.233) 
                         (list -112.651 -188.245) 
                         (list -112.654 -188.257) 
                         (list -112.657 -188.27) 
                         (list -112.661 -188.282) 
                         (list -112.665 -188.294) 
                         (list -112.67 -188.306) 
                         (list -112.676 -188.319) 
                         (list -112.682 -188.331) 
                         (list -112.69 -188.343) 
                         (list -112.698 -188.355) 
                         (list -112.707 -188.368) 
                         (list -112.716 -188.379) 
                         (list -112.726 -188.391) 
                         (list -112.738 -188.403) 
                         (list -112.748 -188.413) 
                         (list -112.759 -188.422) 
                         (list -112.771 -188.431) 
                         (list -112.783 -188.439) 
                         (list -112.794 -188.447) 
                         (list -112.806 -188.455) 
                         (list -112.819 -188.462) 
                         (list -112.831 -188.469) 
                         (list -112.842 -188.476) 
                         (list -112.854 -188.482) 
                         (list -112.864 -188.489) 
                         (list -112.875 -188.495) 
                         (list -112.884 -188.501) 
                         (list -112.892 -188.506) 
                         (list -112.9 -188.512) 
                         (list -112.906 -188.518) 
                         (list -112.91 -188.522) 
                         (list -112.913 -188.526) 
                         (list -112.916 -188.53) 
                         (list -112.917 -188.534) 
                         (list -112.919 -188.541) 
                         (list -112.918 -188.547) 
                         (list -112.912 -188.558) 
                         (list -112.904 -188.568) 
                         (list -112.922 -188.586) 
                         (list -113.121 -188.388) 
                         (list -113.071 -188.55) 
                         (list -113.051 -188.565) 
                         (list -113.262 -188.867) 
                         (list -113.283 -188.852) 
                         (list -113.275 -188.841) 
                         (list -113.268 -188.83) 
                         (list -113.262 -188.819) 
                         (list -113.258 -188.81) 
                         (list -113.254 -188.801) 
                         (list -113.251 -188.793) 
                         (list -113.249 -188.785) 
                         (list -113.248 -188.778) 
                         (list -113.248 -188.771) 
                         (list -113.248 -188.765) 
                         (list -113.249 -188.76) 
                         (list -113.251 -188.755) 
                         (list -113.256 -188.746) 
                         (list -113.264 -188.74) 
                         (list -113.27 -188.736) 
                         (list -113.278 -188.732) 
                         (list -113.286 -188.73) 
                         (list -113.294 -188.729) 
                         (list -113.42 -188.702) 
                         (list -113.572 -188.92) 
                         (list -113.505 -189.018) 
                         (list -113.502 -189.023) 
                         (list -113.498 -189.028) 
                         (list -113.493 -189.033) 
                         (list -113.487 -189.037) 
                         (list -113.477 -189.042) 
                         (list -113.467 -189.046) 
                         (list -113.461 -189.047) 
                         (list -113.455 -189.048) 
                         (list -113.449 -189.047) 
                         (list -113.443 -189.046) 
                         (list -113.436 -189.044) 
                         (list -113.429 -189.041) 
                         (list -113.422 -189.037) 
                         (list -113.415 -189.032) 
                         (list -113.408 -189.026) 
                         (list -113.4 -189.018) 
                         (list -113.393 -189.009) 
                         (list -113.385 -188.999) 
                         (list -113.365 -189.013) 
                         (list -113.497 -189.201) 
                         (list -113.517 -189.187) 
                         (list -113.533 -189.129) 
                         (list -113.533 -189.502) 
                         (list -113.558 -189.502) 
                         (list -113.559 -189.489) 
                         (list -113.561 -189.477) 
                         (list -113.564 -189.467) 
                         (list -113.568 -189.457) 
                         (list -113.573 -189.448) 
                         (list -113.578 -189.441) 
                         (list -113.584 -189.434) 
                         (list -113.591 -189.428) 
                         (list -113.598 -189.423) 
                         (list -113.606 -189.418) 
                         (list -113.613 -189.415) 
                         (list -113.621 -189.412) 
                         (list -113.628 -189.41) 
                         (list -113.635 -189.408) 
                         (list -113.642 -189.408) 
                         (list -113.649 -189.407) 
                         (list -114.215 -189.407) 
                         (list -113.533 -189.7) 
                         (list -113.533 -189.728) 
                         (list -114.217 -190.011) 
                         (list -113.647 -190.011) 
                         (list -113.631 -190.009) 
                         (list -113.615 -190.005) 
                         (list -113.607 -190.002) 
                         (list -113.6 -189.998) 
                         (list -113.593 -189.994) 
                         (list -113.586 -189.989) 
                         (list -113.58 -189.982) 
                         (list -113.575 -189.976) 
                         (list -113.57 -189.968) 
                         (list -113.566 -189.96) 
                         (list -113.563 -189.951) 
                         (list -113.56 -189.94) 
                         (list -113.559 -189.929) 
                         (list -113.558 -189.918) 
                         (list -113.533 -189.918) 
                         (list -113.496 -190.063) 
                         (list -113.382 -190.259) 
                         (list -113.579 -190.648) 
                         (list -113.565 -190.673) 
                         (list -113.349 -190.548) 
                         (list -113.344 -190.545) 
                         (list -113.339 -190.541) 
                         (list -113.333 -190.537) 
                         (list -113.328 -190.532) 
                         (list -113.323 -190.526) 
                         (list -113.318 -190.519) 
                         (list -113.313 -190.512) 
                         (list -113.309 -190.504) 
                         (list -113.306 -190.496) 
                         (list -113.304 -190.487) 
                         (list -113.302 -190.477) 
                         (list -113.302 -190.467) 
                         (list -113.304 -190.456) 
                         (list -113.307 -190.445) 
                         (list -113.311 -190.433) 
                         (list -113.317 -190.421) 
                         (list -113.296 -190.409) 
                         (list -113.109 -190.732) 
                         (list -113.086 -190.722) 
                         (list -112.58 -191.146) 
                         (list -112.534 -191.156) 
                         (list -112.177 -191.265) 
                         (list -112.185 -191.288) 
                         (list -112.195 -191.285) 
                         (list -112.205 -191.284) 
                         (list -112.215 -191.283) 
                         (list -112.225 -191.283) 
                         (list -112.234 -191.284) 
                         (list -112.243 -191.286) 
                         (list -112.251 -191.289) 
                         (list -112.259 -191.293) 
                         (list -112.267 -191.297) 
                         (list -112.274 -191.303) 
                         (list -112.28 -191.309) 
                         (list -112.285 -191.315) 
                         (list -112.291 -191.322) 
                         (list -112.295 -191.33) 
                         (list -112.299 -191.338) 
                         (list -112.302 -191.347) 
                         (list -112.47 -191.878) 
                         "c"
         )
        (command "pline" (list -112.16 -190.654) "w" 0 0 
                         (list -112.104 -190.711) 
                         (list -111.628 -190.725) 
                         (list -111.521 -190.683) 
                         (list -111.521 -190.42) 
                         (list -111.884 -190.059) 
                         (list -111.884 -190.009) 
                         (list -111.301 -189.945) 
                         (list -110.946 -189.527) 
                         (list -110.939 -189.456) 
                         (list -110.953 -189.378) 
                         (list -110.968 -189.357) 
                         (list -111.01 -189.357) 
                         (list -111.031 -189.371) 
                         (list -111.536 -189.874) 
                         (list -111.55 -189.896) 
                         (list -111.592 -189.903) 
                         (list -111.614 -189.888) 
                         (list -111.607 -189.86) 
                         (list -111.585 -189.825) 
                         (list -111.053 -189.257) 
                         (list -111.053 -189.215) 
                         (list -111.067 -189.158) 
                         (list -111.095 -189.151) 
                         (list -111.138 -189.151) 
                         (list -111.734 -189.725) 
                         (list -111.763 -189.732) 
                         (list -111.784 -189.718) 
                         (list -111.784 -189.683) 
                         (list -111.181 -189.087) 
                         (list -111.173 -189.044) 
                         (list -111.181 -189.016) 
                         (list -111.209 -188.988) 
                         (list -111.252 -188.981) 
                         (list -111.287 -188.988) 
                         (list -111.862 -189.541) 
                         (list -111.898 -189.569) 
                         (list -111.919 -189.562) 
                         (list -111.912 -189.527) 
                         (list -111.905 -189.505) 
                         (list -111.379 -188.966) 
                         (list -111.372 -188.924) 
                         (list -111.386 -188.888) 
                         (list -111.422 -188.874) 
                         (list -111.465 -188.874) 
                         (list -111.493 -188.881) 
                         (list -111.99 -189.371) 
                         (list -112.018 -189.378) 
                         (list -112.047 -189.357) 
                         (list -112.409 -189.009) 
                         (list -112.452 -188.995) 
                         (list -112.48 -188.988) 
                         (list -112.558 -188.995) 
                         (list -112.587 -189.044) 
                         (list -112.622 -189.08) 
                         (list -112.636 -189.101) 
                         (list -112.75 -189.115) 
                         (list -112.75 -189.165) 
                         (list -112.699 -189.224) 
                         (list -112.65 -189.285) 
                         (list -112.603 -189.347) 
                         (list -112.559 -189.411) 
                         (list -112.516 -189.476) 
                         (list -112.476 -189.543) 
                         (list -112.438 -189.61) 
                         (list -112.402 -189.68) 
                         (list -112.369 -189.75) 
                         (list -112.338 -189.821) 
                         (list -112.309 -189.894) 
                         (list -112.283 -189.967) 
                         (list -112.259 -190.041) 
                         (list -112.238 -190.116) 
                         (list -112.219 -190.192) 
                         (list -112.203 -190.268) 
                         (list -112.189 -190.344) 
                         (list -112.178 -190.422) 
                         (list -112.17 -190.499) 
                         (list -112.164 -190.577) 
                         "c"
         )
  (command "style" "ht" "simhei.ttf" "" "" "" "" "" "")
  (setq c_date (rtos (getvar "CDATE")))
  (setq	c_date (strcat (substr c_date 1 4)
		       "/"
		       (substr c_date 5 2)
		       "/"
		       (substr c_date 7 2)
	       )
  )
  (setq	txt_dt (list (cons 0 "TEXT")
		     (cons 1 c_date)
		     (cons 10 (trans (list -100 -192 0) 1 0))
		     (cons 40 3)
		     (cons 7 "ht")
	       )
  )
  (entmake txt_dt)
  )
(defun gd ()
  (command "pline"
	   (list -94.9228 -174.994)
	   "w"
	   0
	   0
	   (list -94.8668 -175.051)
	   (list -94.3908 -175.065)
	   (list -94.2838 -175.023)
	   (list -94.2838 -174.76)
	   (list -94.6468 -174.399)
	   (list -94.6468 -174.349)
	   (list -94.0638 -174.285)
	   (list -93.7088 -173.867)
	   (list -93.7018 -173.796)
	   (list -93.7158 -173.718)
	   (list -93.7308 -173.697)
	   (list -93.7728 -173.697)
	   (list -93.7938 -173.711)
	   (list -94.2988 -174.214)
	   (list -94.3128 -174.236)
	   (list -94.3548 -174.243)
	   (list -94.3768 -174.228)
	   (list -94.3698 -174.2)
	   (list -94.3478 -174.165)
	   (list -93.8158 -173.597)
	   (list -93.8158 -173.555)
	   (list -93.8298 -173.498)
	   (list -93.8578 -173.491)
	   (list -93.9008 -173.491)
	   (list -94.4968 -174.065)
	   (list -94.5258 -174.072)
	   (list -94.5468 -174.058)
	   (list -94.5468 -174.023)
	   (list -93.9438 -173.427)
	   (list -93.9358 -173.384)
	   (list -93.9438 -173.356)
	   (list -93.9718 -173.328)
	   (list -94.0148 -173.321)
	   (list -94.0498 -173.328)
	   (list -94.6248 -173.881)
	   (list -94.6608 -173.909)
	   (list -94.6818 -173.902)
	   (list -94.6748 -173.867)
	   (list -94.6678 -173.845)
	   (list -94.1418 -173.306)
	   (list -94.1348 -173.264)
	   (list -94.1488 -173.228)
	   (list -94.1848 -173.214)
	   (list -94.2278 -173.214)
	   (list -94.2558 -173.221)
	   (list -94.7528 -173.711)
	   (list -94.7808 -173.718)
	   (list -94.8098 -173.697)
	   (list -95.1718 -173.349)
	   (list -95.2148 -173.335)
	   (list -95.2428 -173.328)
	   (list -95.3208 -173.335)
	   (list -95.3498 -173.384)
	   (list -95.3848 -173.42)
	   (list -95.3988 -173.441)
	   (list -95.5128 -173.455)
	   (list -95.5128 -173.505)
	   (list -95.4618 -173.564)
	   (list -95.4128 -173.625)
	   (list -95.3658 -173.687)
	   (list -95.3218 -173.751)
	   (list -95.2788 -173.816)
	   (list -95.2388 -173.883)
	   (list -95.2008 -173.95)
	   (list -95.1648 -174.02)
	   (list -95.1318 -174.09)
	   (list -95.1008 -174.161)
	   (list -95.0718 -174.234)
	   (list -95.0458 -174.307)
	   (list -95.0218 -174.381)
	   (list -95.0008 -174.456)
	   (list -94.9818 -174.532)
	   (list -94.9658 -174.608)
	   (list -94.9518 -174.684)
	   (list -94.9408 -174.762)
	   (list -94.9328 -174.839)
	   (list -94.9268 -174.917)
	   "c"
  )
  (command "pline"
	   (list -95.2348 -176.226)
	   "w"
	   0
	   0
	   (list -95.2358 -176.234)
	   (list -95.2368 -176.243)
	   (list -95.2358 -176.251)
	   (list -95.2348 -176.259)
	   (list -95.2328 -176.267)
	   (list -95.2298 -176.275)
	   (list -95.2268 -176.283)
	   (list -95.2218 -176.29)
	   (list -95.2168 -176.297)
	   (list -95.2108 -176.303)
	   (list -95.2038 -176.309)
	   (list -95.1958 -176.315)
	   (list -95.1878 -176.32)
	   (list -95.1778 -176.324)
	   (list -95.1678 -176.328)
	   (list -95.1758 -176.352)
	   (list -94.9998 -176.338)
	   (list -94.9998 -176.313)
	   (list -94.9898 -176.313)
	   (list -94.9798 -176.311)
	   (list -94.9698 -176.309)
	   (list -94.9618 -176.306)
	   (list -94.9528 -176.303)
	   (list -94.9458 -176.298)
	   (list -94.9388 -176.293)
	   (list -94.9318 -176.288)
	   (list -94.9268 -176.282)
	   (list -94.9218 -176.276)
	   (list -94.9168 -176.269)
	   (list -94.9138 -176.262)
	   (list -94.9108 -176.255)
	   (list -94.9088 -176.248)
	   (list -94.9078 -176.24)
	   (list -94.9068 -176.233)
	   (list -94.9068 -175.81)
	   (list -94.9068 -175.8)
	   (list -94.9068 -175.79)
	   (list -94.9058 -175.78)
	   (list -94.9048 -175.771)
	   (list -94.9048 -175.761)
	   (list -94.9038 -175.753)
	   (list -94.9018 -175.744)
	   (list -94.9008 -175.735)
	   (list -94.8978 -175.719)
	   (list -94.8928 -175.703)
	   (list -94.8888 -175.688)
	   (list -94.8828 -175.675)
	   (list -94.8768 -175.661)
	   (list -94.8708 -175.649)
	   (list -94.8628 -175.637)
	   (list -94.8558 -175.627)
	   (list -94.8468 -175.616)
	   (list -94.8388 -175.607)
	   (list -94.8288 -175.598)
	   (list -94.8188 -175.59)
	   (list -94.8088 -175.582)
	   (list -94.7978 -175.575)
	   (list -94.7868 -175.569)
	   (list -94.7748 -175.563)
	   (list -94.7638 -175.558)
	   (list -94.7508 -175.554)
	   (list -94.7388 -175.549)
	   (list -94.7258 -175.546)
	   (list -94.7118 -175.543)
	   (list -94.6988 -175.54)
	   (list -94.6848 -175.538)
	   (list -94.6708 -175.537)
	   (list -94.6568 -175.535)
	   (list -94.6418 -175.534)
	   (list -94.6278 -175.534)
	   (list -94.6128 -175.534)
	   (list -94.5988 -175.534)
	   (list -94.5848 -175.535)
	   (list -94.5708 -175.536)
	   (list -94.5568 -175.538)
	   (list -94.5428 -175.54)
	   (list -94.5288 -175.543)
	   (list -94.5158 -175.546)
	   (list -94.5018 -175.55)
	   (list -94.4888 -175.554)
	   (list -94.4758 -175.559)
	   (list -94.4628 -175.564)
	   (list -94.4508 -175.569)
	   (list -94.4388 -175.575)
	   (list -94.4268 -175.582)
	   (list -94.4158 -175.589)
	   (list -94.4048 -175.596)
	   (list -94.3938 -175.603)
	   (list -94.3838 -175.611)
	   (list -94.3748 -175.62)
	   (list -94.3658 -175.628)
	   (list -94.3568 -175.638)
	   (list -94.3488 -175.647)
	   (list -94.3418 -175.657)
	   (list -94.3348 -175.667)
	   (list -94.3288 -175.677)
	   (list -94.3238 -175.688)
	   (list -94.3188 -175.699)
	   (list -94.3158 -175.71)
	   (list -94.3128 -175.722)
	   (list -94.3108 -175.734)
	   (list -94.3088 -175.746)
	   (list -94.3088 -175.758)
	   (list -94.3088 -176.219)
	   (list -94.3088 -176.226)
	   (list -94.3078 -176.233)
	   (list -94.3068 -176.241)
	   (list -94.3058 -176.248)
	   (list -94.3028 -176.256)
	   (list -94.2998 -176.264)
	   (list -94.2958 -176.272)
	   (list -94.2918 -176.279)
	   (list -94.2858 -176.286)
	   (list -94.2798 -176.292)
	   (list -94.2718 -176.298)
	   (list -94.2628 -176.304)
	   (list -94.2528 -176.308)
	   (list -94.2418 -176.311)
	   (list -94.2348 -176.312)
	   (list -94.2288 -176.313)
	   (list -94.2218 -176.313)
	   (list -94.2138 -176.313)
	   (list -94.2138 -176.338)
	   (list -93.9458 -176.255)
	   (list -94.0468 -175.987)
	   (list -94.0108 -175.974)
	   (list -93.9988 -175.991)
	   (list -93.9848 -176.007)
	   (list -93.9708 -176.023)
	   (list -93.9558 -176.039)
	   (list -93.9408 -176.055)
	   (list -93.9238 -176.07)
	   (list -93.9068 -176.083)
	   (list -93.8888 -176.096)
	   (list -93.8698 -176.107)
	   (list -93.8508 -176.115)
	   (list -93.8298 -176.122)
	   (list -93.8088 -176.127)
	   (list -93.7868 -176.129)
	   (list -93.7648 -176.128)
	   (list -93.7538 -176.127)
	   (list -93.7418 -176.124)
	   (list -93.7298 -176.121)
	   (list -93.7178 -176.117)
	   (list -93.7078 -176.113)
	   (list -93.6968 -176.109)
	   (list -93.6868 -176.103)
	   (list -93.6758 -176.096)
	   (list -93.6648 -176.088)
	   (list -93.6548 -176.08)
	   (list -93.6448 -176.071)
	   (list -93.6358 -176.061)
	   (list -93.6278 -176.05)
	   (list -93.6208 -176.038)
	   (list -93.6148 -176.026)
	   (list -93.6108 -176.013)
	   (list -93.6088 -175.999)
	   (list -93.6088 -175.985)
	   (list -93.6108 -175.97)
	   (list -93.6148 -175.954)
	   (list -93.6208 -175.941)
	   (list -93.6288 -175.929)
	   (list -93.6378 -175.918)
	   (list -93.6478 -175.909)
	   (list -93.6578 -175.901)
	   (list -93.6698 -175.894)
	   (list -93.6808 -175.889)
	   (list -93.6938 -175.884)
	   (list -93.7058 -175.88)
	   (list -93.7168 -175.877)
	   (list -93.7288 -175.874)
	   (list -93.7398 -175.872)
	   (list -93.7488 -175.871)
	   (list -93.7578 -175.87)
	   (list -93.7658 -175.869)
	   (list -93.7708 -175.869)
	   (list -93.8838 -175.861)
	   (list -93.9068 -175.859)
	   (list -93.9308 -175.855)
	   (list -93.9538 -175.849)
	   (list -93.9758 -175.842)
	   (list -93.9978 -175.833)
	   (list -94.0178 -175.824)
	   (list -94.0378 -175.813)
	   (list -94.0568 -175.801)
	   (list -94.0748 -175.788)
	   (list -94.0908 -175.774)
	   (list -94.1058 -175.76)
	   (list -94.1198 -175.744)
	   (list -94.1318 -175.728)
	   (list -94.1428 -175.712)
	   (list -94.1518 -175.695)
	   (list -94.1588 -175.678)
	   (list -94.1648 -175.659)
	   (list -94.1678 -175.639)
	   (list -94.1688 -175.618)
	   (list -94.1678 -175.596)
	   (list -94.1638 -175.573)
	   (list -94.1588 -175.55)
	   (list -94.1508 -175.528)
	   (list -94.1408 -175.506)
	   (list -94.1288 -175.484)
	   (list -94.1158 -175.463)
	   (list -94.0998 -175.443)
	   (list -94.0818 -175.425)
	   (list -94.0618 -175.408)
	   (list -94.0408 -175.392)
	   (list -94.0288 -175.386)
	   (list -94.0178 -175.379)
	   (list -94.0048 -175.374)
	   (list -93.9918 -175.369)
	   (list -93.9718 -175.361)
	   (list -93.9518 -175.355)
	   (list -93.9338 -175.351)
	   (list -93.9158 -175.347)
	   (list -93.8998 -175.343)
	   (list -93.8848 -175.341)
	   (list -93.8708 -175.339)
	   (list -93.8578 -175.338)
	   (list -93.8458 -175.337)
	   (list -93.8348 -175.336)
	   (list -93.8248 -175.336)
	   (list -93.8148 -175.335)
	   (list -93.7988 -175.333)
	   (list -93.7868 -175.33)
	   (list -93.7778 -175.326)
	   (list -93.7718 -175.321)
	   (list -93.7678 -175.315)
	   (list -93.7648 -175.309)
	   (list -93.7628 -175.296)
	   (list -93.7638 -175.285)
	   (list -93.7338 -175.275)
	   (list -94.0558 -174.954)
	   (list -94.0878 -174.974)
	   (list -94.1208 -174.994)
	   (list -94.1538 -175.012)
	   (list -94.1878 -175.029)
	   (list -94.2228 -175.045)
	   (list -94.2578 -175.059)
	   (list -94.2928 -175.073)
	   (list -94.3298 -175.085)
	   (list -94.3658 -175.096)
	   (list -94.4028 -175.105)
	   (list -94.4398 -175.114)
	   (list -94.4768 -175.121)
	   (list -94.5148 -175.127)
	   (list -94.5528 -175.131)
	   (list -94.5908 -175.134)
	   (list -94.6288 -175.136)
	   (list -94.6668 -175.137)
	   (list -94.7048 -175.136)
	   (list -94.7428 -175.134)
	   (list -94.7808 -175.13)
	   (list -94.8188 -175.125)
	   (list -94.8558 -175.119)
	   (list -94.8938 -175.112)
	   (list -94.9308 -175.103)
	   (list -94.9678 -175.093)
	   (list -95.0038 -175.082)
	   (list -95.0398 -175.07)
	   (list -95.0758 -175.056)
	   (list -95.1108 -175.041)
	   (list -95.1448 -175.025)
	   (list -95.1788 -175.007)
	   (list -95.2118 -174.989)
	   (list -95.2448 -174.969)
	   (list -95.2768 -174.949)
	   (list -95.3078 -174.927)
	   (list -95.3388 -174.904)
	   (list -95.3678 -174.88)
	   (list -95.3968 -174.855)
	   (list -95.4248 -174.829)
	   (list -95.4518 -174.802)
	   (list -95.4778 -174.774)
	   (list -95.5028 -174.745)
	   (list -95.5268 -174.716)
	   (list -95.5498 -174.685)
	   (list -95.5718 -174.654)
	   (list -95.5918 -174.622)
	   (list -95.6118 -174.59)
	   (list -95.6308 -174.557)
	   (list -95.6478 -174.523)
	   (list -95.6638 -174.488)
	   (list -95.6788 -174.453)
	   (list -95.6928 -174.418)
	   (list -95.7058 -174.382)
	   (list -95.7168 -174.345)
	   (list -95.7268 -174.309)
	   (list -95.7358 -174.272)
	   (list -95.7428 -174.234)
	   (list -95.7488 -174.197)
	   (list -95.7538 -174.159)
	   (list -95.7578 -174.121)
	   (list -95.7598 -174.083)
	   (list -95.7608 -174.045)
	   (list -95.7598 -174.007)
	   (list -95.7578 -173.969)
	   (list -95.7548 -173.931)
	   (list -95.7508 -173.893)
	   (list -95.7448 -173.855)
	   (list -95.7378 -173.818)
	   (list -95.7298 -173.781)
	   (list -95.7198 -173.744)
	   (list -95.7088 -173.707)
	   (list -95.6968 -173.671)
	   (list -95.6838 -173.635)
	   (list -95.6688 -173.6)
	   (list -95.6538 -173.566)
	   (list -95.6368 -173.532)
	   (list -95.6178 -173.498)
	   (list -95.5988 -173.465)
	   (list -95.5788 -173.433)
	   (list -95.5568 -173.402)
	   (list -95.5348 -173.371)
	   (list -95.5108 -173.341)
	   (list -95.4858 -173.312)
	   (list -95.4598 -173.284)
	   (list -95.4338 -173.257)
	   (list -95.4058 -173.231)
	   (list -95.3778 -173.205)
	   (list -95.3478 -173.181)
	   (list -95.3178 -173.158)
	   (list -95.2868 -173.135)
	   (list -95.2558 -173.114)
	   (list -95.2228 -173.094)
	   (list -95.1898 -173.075)
	   (list -95.1568 -173.058)
	   (list -95.1218 -173.041)
	   (list -95.0868 -173.026)
	   (list -95.0518 -173.012)
	   (list -95.0158 -172.999)
	   (list -94.9798 -172.987)
	   (list -94.9428 -172.977)
	   (list -94.9058 -172.968)
	   (list -94.8688 -172.96)
	   (list -94.8308 -172.953)
	   (list -94.7938 -172.948)
	   (list -94.7558 -172.944)
	   (list -94.7178 -172.942)
	   (list -94.6798 -172.94)
	   (list -94.6418 -172.941)
	   (list -94.6038 -172.942)
	   (list -94.5658 -172.945)
	   (list -94.5278 -172.949)
	   (list -94.4898 -172.954)
	   (list -94.4528 -172.961)
	   (list -94.4148 -172.969)
	   (list -94.3778 -172.978)
	   (list -94.3418 -172.988)
	   (list -94.3048 -173.0)
	   (list -94.2698 -173.013)
	   (list -94.2338 -173.027)
	   (list -94.1998 -173.043)
	   (list -94.1648 -173.059)
	   (list -94.1318 -173.077)
	   (list -94.0988 -173.096)
	   (list -94.0658 -173.116)
	   (list -94.0198 -172.854)
	   (list -93.8478 -172.884)
	   (list -93.8148 -172.696)
	   (list -93.6308 -172.728)
	   (list -93.5978 -172.536)
	   (list -93.4178 -172.568)
	   (list -93.3878 -172.397)
	   (list -93.2038 -172.429)
	   (list -93.1698 -172.237)
	   (list -93.0078 -172.266)
	   (list -92.9728 -172.065)
	   (list -92.7286 -172.108)
	   (list -92.7968 -172.041)
	   (list -92.8668 -171.978)
	   (list -92.9388 -171.916)
	   (list -93.0128 -171.857)
	   (list -93.0888 -171.801)
	   (list -93.1678 -171.747)
	   (list -93.2478 -171.696)
	   (list -93.3288 -171.648)
	   (list -93.4128 -171.603)
	   (list -93.4978 -171.561)
	   (list -93.5838 -171.522)
	   (list -93.6718 -171.485)
	   (list -93.7608 -171.452)
	   (list -93.8508 -171.422)
	   (list -93.9418 -171.395)
	   (list -94.0328 -171.372)
	   (list -94.1258 -171.351)
	   (list -94.2188 -171.334)
	   (list -94.3128 -171.32)
	   (list -94.4068 -171.309)
	   (list -94.5018 -171.302)
	   (list -94.5968 -171.298)
	   (list -94.6918 -171.297)
	   (list -94.7858 -171.299)
	   (list -94.8808 -171.305)
	   (list -94.9748 -171.314)
	   (list -95.0688 -171.327)
	   (list -95.1628 -171.342)
	   (list -95.2558 -171.361)
	   (list -95.3478 -171.383)
	   (list -95.4398 -171.409)
	   (list -95.5298 -171.437)
	   (list -95.6188 -171.469)
	   (list -95.7078 -171.503)
	   (list -95.7948 -171.541)
	   (list -95.8798 -171.582)
	   (list -95.9648 -171.626)
	   (list -96.0468 -171.672)
	   (list -96.1278 -171.722)
	   (list -96.2068 -171.774)
	   (list -96.2838 -171.829)
	   (list -96.3598 -171.887)
	   (list -96.4328 -171.947)
	   (list -96.5038 -172.01)
	   (list -96.5728 -172.075)
	   (list -96.6388 -172.143)
	   (list -96.7038 -172.213)
	   (list -96.7648 -172.285)
	   (list -96.8238 -172.359)
	   (list -96.8808 -172.435)
	   (list -96.9348 -172.513)
	   (list -96.9858 -172.593)
	   (list -97.0338 -172.675)
	   (list -97.0798 -172.758)
	   (list -97.1218 -172.843)
	   (list -97.1618 -172.929)
	   (list -97.1978 -173.016)
	   (list -97.2308 -173.105)
	   (list -97.2618 -173.195)
	   (list -97.2888 -173.286)
	   (list -97.3128 -173.378)
	   (list -97.3328 -173.47)
	   (list -97.3508 -173.564)
	   (list -97.3648 -173.657)
	   (list -97.3758 -173.752)
	   (list -97.3838 -173.846)
	   (list -97.3878 -173.941)
	   (list -97.3888 -174.036)
	   (list -97.3868 -174.131)
	   (list -97.3808 -174.225)
	   (list -97.3728 -174.32)
	   (list -97.3598 -174.414)
	   (list -97.3448 -174.507)
	   (list -97.3258 -174.6)
	   (list -97.3038 -174.693)
	   (list -97.2788 -174.784)
	   (list -97.2508 -174.875)
	   (list -97.2198 -174.964)
	   (list -97.1848 -175.052)
	   (list -97.1478 -175.14)
	   (list -97.1068 -175.225)
	   (list -97.0638 -175.31)
	   (list -97.0168 -175.392)
	   (list -96.9678 -175.473)
	   (list -96.9158 -175.553)
	   (list -96.8608 -175.63)
	   (list -96.8038 -175.705)
	   (list -96.7438 -175.779)
	   (list -96.6808 -175.85)
	   (list -96.6158 -175.919)
	   (list -96.5478 -175.986)
	   (list -96.4788 -176.05)
	   (list -96.4068 -176.112)
	   (list -96.3328 -176.171)
	   (list -96.2568 -176.228)
	   (list -96.1788 -176.282)
	   (list -96.0988 -176.334)
	   (list -96.0178 -176.382)
	   (list -95.9348 -176.428)
	   (list -95.8498 -176.47)
	   (list -95.7638 -176.51)
	   (list -95.6758 -176.547)
	   (list -95.5878 -176.58)
	   (list -95.4978 -176.611)
	   (list -95.4068 -176.638)
	   (list -95.3148 -176.662)
	   (list -95.2228 -176.683)
	   (list -95.1298 -176.701)
	   (list -95.0358 -176.716)
	   (list -94.9418 -176.727)
	   (list -94.8468 -176.735)
	   (list -94.7518 -176.739)
	   (list -94.6578 -176.741)
	   (list -94.5628 -176.739)
	   (list -94.4678 -176.733)
	   (list -94.3738 -176.725)
	   (list -94.2788 -176.713)
	   (list -94.1858 -176.698)
	   (list -94.0928 -176.679)
	   (list -93.9998 -176.658)
	   (list -93.9088 -176.633)
	   (list -93.8178 -176.605)
	   (list -93.7288 -176.574)
	   (list -93.6398 -176.539)
	   (list -93.5528 -176.502)
	   (list -93.4668 -176.462)
	   (list -93.3828 -176.419)
	   (list -93.2998 -176.372)
	   (list -93.2188 -176.323)
	   (list -93.1388 -176.271)
	   (list -93.0618 -176.217)
	   (list -92.9858 -176.16)
	   (list -92.9128 -176.1)
	   (list -93.6458 -175.512)
	   (list -93.6838 -175.526)
	   (list -93.6918 -175.515)
	   (list -93.7008 -175.504)
	   (list -93.7098 -175.494)
	   (list -93.7178 -175.484)
	   (list -93.7268 -175.475)
	   (list -93.7358 -175.467)
	   (list -93.7438 -175.459)
	   (list -93.7528 -175.451)
	   (list -93.7698 -175.438)
	   (list -93.7868 -175.427)
	   (list -93.8028 -175.418)
	   (list -93.8198 -175.411)
	   (list -93.8358 -175.405)
	   (list -93.8528 -175.402)
	   (list -93.8688 -175.4)
	   (list -93.8858 -175.399)
	   (list -93.9018 -175.4)
	   (list -93.9188 -175.403)
	   (list -93.9348 -175.407)
	   (list -93.9518 -175.412)
	   (list -93.9638 -175.417)
	   (list -93.9738 -175.422)
	   (list -93.9838 -175.428)
	   (list -93.9928 -175.434)
	   (list -94.0088 -175.449)
	   (list -94.0208 -175.465)
	   (list -94.0288 -175.483)
	   (list -94.0328 -175.501)
	   (list -94.0338 -175.511)
	   (list -94.0328 -175.521)
	   (list -94.0308 -175.53)
	   (list -94.0278 -175.54)
	   (list -94.0238 -175.551)
	   (list -94.0178 -175.562)
	   (list -94.0118 -175.571)
	   (list -94.0048 -175.58)
	   (list -93.9888 -175.594)
	   (list -93.9708 -175.605)
	   (list -93.9598 -175.61)
	   (list -93.9488 -175.614)
	   (list -93.9378 -175.618)
	   (list -93.9248 -175.621)
	   (list -93.9118 -175.623)
	   (list -93.8988 -175.625)
	   (list -93.8848 -175.627)
	   (list -93.8698 -175.629)
	   (list -93.7328 -175.64)
	   (list -93.7118 -175.643)
	   (list -93.6908 -175.647)
	   (list -93.6708 -175.652)
	   (list -93.6518 -175.658)
	   (list -93.6328 -175.665)
	   (list -93.6158 -175.674)
	   (list -93.5998 -175.684)
	   (list -93.5838 -175.695)
	   (list -93.5698 -175.708)
	   (list -93.5558 -175.721)
	   (list -93.5438 -175.736)
	   (list -93.5318 -175.752)
	   (list -93.5208 -175.77)
	   (list -93.5108 -175.788)
	   (list -93.5018 -175.807)
	   (list -93.4928 -175.828)
	   (list -93.4878 -175.844)
	   (list -93.4838 -175.859)
	   (list -93.4808 -175.874)
	   (list -93.4778 -175.889)
	   (list -93.4768 -175.903)
	   (list -93.4758 -175.917)
	   (list -93.4768 -175.931)
	   (list -93.4768 -175.944)
	   (list -93.4788 -175.957)
	   (list -93.4818 -175.97)
	   (list -93.4848 -175.982)
	   (list -93.4888 -175.994)
	   (list -93.4988 -176.017)
	   (list -93.5118 -176.038)
	   (list -93.5258 -176.058)
	   (list -93.5428 -176.077)
	   (list -93.5598 -176.094)
	   (list -93.5798 -176.109)
	   (list -93.5998 -176.123)
	   (list -93.6218 -176.135)
	   (list -93.6438 -176.146)
	   (list -93.6668 -176.155)
	   (list -93.6848 -176.161)
	   (list -93.7018 -176.166)
	   (list -93.7188 -176.17)
	   (list -93.7348 -176.173)
	   (list -93.7498 -176.175)
	   (list -93.7638 -176.177)
	   (list -93.7778 -176.178)
	   (list -93.7908 -176.179)
	   (list -93.8038 -176.179)
	   (list -93.8158 -176.18)
	   (list -93.8278 -176.18)
	   (list -93.8388 -176.181)
	   (list -93.8588 -176.184)
	   (list -93.8778 -176.189)
	   (list -93.8878 -176.193)
	   (list -93.8958 -176.199)
	   (list -93.9028 -176.206)
	   (list -93.9078 -176.213)
	   (list -93.9118 -176.221)
	   (list -93.9138 -176.229)
	   (list -93.9148 -176.236)
	   (list -93.9128 -176.243)
	   (list -93.9458 -176.255)
	   (list -94.2138 -176.338)
	   (list -94.5878 -176.338)
	   (list -94.5878 -176.313)
	   (list -94.5738 -176.313)
	   (list -94.5608 -176.311)
	   (list -94.5498 -176.308)
	   (list -94.5398 -176.304)
	   (list -94.5308 -176.298)
	   (list -94.5228 -176.293)
	   (list -94.5168 -176.286)
	   (list -94.5108 -176.28)
	   (list -94.5058 -176.272)
	   (list -94.5018 -176.265)
	   (list -94.4988 -176.257)
	   (list -94.4968 -176.25)
	   (list -94.4948 -176.242)
	   (list -94.4938 -176.235)
	   (list -94.4928 -176.229)
	   (list -94.4928 -176.223)
	   (list -94.4928 -175.782)
	   (list -94.4928 -175.77)
	   (list -94.4938 -175.757)
	   (list -94.4948 -175.742)
	   (list -94.4968 -175.727)
	   (list -94.4988 -175.719)
	   (list -94.5008 -175.711)
	   (list -94.5028 -175.702)
	   (list -94.5048 -175.694)
	   (list -94.5108 -175.678)
	   (list -94.5188 -175.662)
	   (list -94.5228 -175.654)
	   (list -94.5278 -175.647)
	   (list -94.5338 -175.639)
	   (list -94.5398 -175.632)
	   (list -94.5468 -175.626)
	   (list -94.5538 -175.619)
	   (list -94.5618 -175.614)
	   (list -94.5708 -175.608)
	   (list -94.5798 -175.603)
	   (list -94.5898 -175.599)
	   (list -94.5998 -175.595)
	   (list -94.6118 -175.592)
	   (list -94.6238 -175.589)
	   (list -94.6368 -175.587)
	   (list -94.6508 -175.586)
	   (list -94.6658 -175.586)
	   (list -94.6798 -175.586)
	   (list -94.6928 -175.587)
	   (list -94.7048 -175.588)
	   (list -94.7168 -175.59)
	   (list -94.7278 -175.593)
	   (list -94.7388 -175.596)
	   (list -94.7488 -175.6)
	   (list -94.7588 -175.604)
	   (list -94.7678 -175.608)
	   (list -94.7768 -175.613)
	   (list -94.7848 -175.619)
	   (list -94.7928 -175.625)
	   (list -94.7998 -175.631)
	   (list -94.8068 -175.638)
	   (list -94.8128 -175.645)
	   (list -94.8188 -175.653)
	   (list -94.8248 -175.661)
	   (list -94.8298 -175.669)
	   (list -94.8338 -175.677)
	   (list -94.8388 -175.686)
	   (list -94.8428 -175.696)
	   (list -94.8458 -175.705)
	   (list -94.8488 -175.715)
	   (list -94.8518 -175.725)
	   (list -94.8538 -175.735)
	   (list -94.8558 -175.745)
	   (list -94.8578 -175.756)
	   (list -94.8588 -175.767)
	   (list -94.8608 -175.778)
	   (list -94.8608 -175.789)
	   (list -94.8618 -175.801)
	   (list -94.8618 -175.812)
	   (list -94.8618 -176.229)
	   (list -94.8608 -176.237)
	   (list -94.8598 -176.245)
	   (list -94.8578 -176.253)
	   (list -94.8558 -176.261)
	   (list -94.8518 -176.268)
	   (list -94.8478 -176.275)
	   (list -94.8428 -176.282)
	   (list -94.8378 -176.288)
	   (list -94.8318 -176.293)
	   (list -94.8248 -176.298)
	   (list -94.8168 -176.303)
	   (list -94.8088 -176.306)
	   (list -94.7998 -176.309)
	   (list -94.7908 -176.311)
	   (list -94.7798 -176.313)
	   (list -94.7698 -176.313)
	   (list -94.7698 -176.338)
	   (list -94.9998 -176.338)
	   (list -95.1758 -176.352)
	   (list -95.5538 -176.232)
	   (list -95.5638 -176.229)
	   (list -95.5728 -176.226)
	   (list -95.5828 -176.222)
	   (list -95.5928 -176.217)
	   (list -95.6028 -176.213)
	   (list -95.6118 -176.208)
	   (list -95.6218 -176.202)
	   (list -95.6318 -176.197)
	   (list -95.6418 -176.191)
	   (list -95.6508 -176.184)
	   (list -95.6608 -176.177)
	   (list -95.6688 -176.17)
	   (list -95.6778 -176.163)
	   (list -95.6868 -176.155)
	   (list -95.6948 -176.146)
	   (list -95.7028 -176.138)
	   (list -95.7098 -176.129)
	   (list -95.7168 -176.119)
	   (list -95.7228 -176.11)
	   (list -95.7278 -176.099)
	   (list -95.7338 -176.089)
	   (list -95.7378 -176.078)
	   (list -95.7418 -176.067)
	   (list -95.7448 -176.055)
	   (list -95.7468 -176.043)
	   (list -95.7488 -176.031)
	   (list -95.7488 -176.018)
	   (list -95.7488 -176.005)
	   (list -95.7478 -175.992)
	   (list -95.7458 -175.978)
	   (list -95.7428 -175.964)
	   (list -95.7388 -175.949)
	   (list -95.7348 -175.938)
	   (list -95.7298 -175.926)
	   (list -95.7248 -175.916)
	   (list -95.7188 -175.905)
	   (list -95.7128 -175.896)
	   (list -95.7058 -175.887)
	   (list -95.6988 -175.878)
	   (list -95.6908 -175.87)
	   (list -95.6828 -175.862)
	   (list -95.6748 -175.855)
	   (list -95.6658 -175.848)
	   (list -95.6568 -175.842)
	   (list -95.6468 -175.836)
	   (list -95.6368 -175.831)
	   (list -95.6268 -175.826)
	   (list -95.6168 -175.822)
	   (list -95.6058 -175.819)
	   (list -95.5948 -175.816)
	   (list -95.5838 -175.813)
	   (list -95.5718 -175.811)
	   (list -95.5608 -175.809)
	   (list -95.5488 -175.808)
	   (list -95.5378 -175.807)
	   (list -95.5258 -175.807)
	   (list -95.5128 -175.807)
	   (list -95.5018 -175.808)
	   (list -95.4888 -175.809)
	   (list -95.4768 -175.811)
	   (list -95.4648 -175.813)
	   (list -95.4528 -175.816)
	   (list -95.4408 -175.819)
	   (list -95.4288 -175.822)
	   (list -95.3128 -175.859)
	   (list -95.2408 -175.631)
	   (list -95.2388 -175.625)
	   (list -95.2378 -175.618)
	   (list -95.2368 -175.61)
	   (list -95.2358 -175.603)
	   (list -95.2358 -175.595)
	   (list -95.2368 -175.587)
	   (list -95.2378 -175.578)
	   (list -95.2408 -175.57)
	   (list -95.2438 -175.562)
	   (list -95.2488 -175.554)
	   (list -95.2538 -175.546)
	   (list -95.2608 -175.539)
	   (list -95.2688 -175.532)
	   (list -95.2788 -175.526)
	   (list -95.2898 -175.521)
	   (list -95.3028 -175.516)
	   (list -95.2968 -175.496)
	   (list -95.3428 -175.486)
	   (list -95.3588 -175.504)
	   (list -95.3678 -175.497)
	   (list -95.3778 -175.491)
	   (list -95.3868 -175.486)
	   (list -95.3968 -175.483)
	   (list -95.4058 -175.481)
	   (list -95.4148 -175.48)
	   (list -95.4248 -175.48)
	   (list -95.4328 -175.481)
	   (list -95.4418 -175.483)
	   (list -95.4498 -175.485)
	   (list -95.4568 -175.488)
	   (list -95.4648 -175.492)
	   (list -95.4718 -175.497)
	   (list -95.4778 -175.502)
	   (list -95.4838 -175.507)
	   (list -95.4888 -175.513)
	   (list -95.8468 -175.939)
	   (list -95.8518 -175.946)
	   (list -95.8558 -175.953)
	   (list -95.8598 -175.96)
	   (list -95.8628 -175.968)
	   (list -95.8648 -175.976)
	   (list -95.8668 -175.984)
	   (list -95.8678 -175.992)
	   (list -95.8668 -176.001)
	   (list -95.8658 -176.009)
	   (list -95.8638 -176.018)
	   (list -95.8608 -176.026)
	   (list -95.8568 -176.035)
	   (list -95.8518 -176.043)
	   (list -95.8458 -176.051)
	   (list -95.8388 -176.059)
	   (list -95.8308 -176.067)
	   (list -95.8468 -176.086)
	   (list -96.3458 -175.667)
	   (list -96.1928 -175.485)
	   (list -96.1748 -175.501)
	   (list -96.1818 -175.513)
	   (list -96.1888 -175.524)
	   (list -96.1948 -175.536)
	   (list -96.1998 -175.547)
	   (list -96.2048 -175.558)
	   (list -96.2088 -175.569)
	   (list -96.2118 -175.58)
	   (list -96.2148 -175.591)
	   (list -96.2168 -175.601)
	   (list -96.2188 -175.611)
	   (list -96.2198 -175.621)
	   (list -96.2198 -175.631)
	   (list -96.2198 -175.64)
	   (list -96.2198 -175.649)
	   (list -96.2188 -175.658)
	   (list -96.2178 -175.667)
	   (list -96.2158 -175.676)
	   (list -96.2128 -175.684)
	   (list -96.2108 -175.692)
	   (list -96.2078 -175.7)
	   (list -96.2008 -175.715)
	   (list -96.1928 -175.729)
	   (list -96.1838 -175.743)
	   (list -96.1748 -175.755)
	   (list -96.1638 -175.767)
	   (list -96.1528 -175.777)
	   (list -96.0718 -175.848)
	   (list -96.0658 -175.853)
	   (list -96.0608 -175.856)
	   (list -96.0548 -175.86)
	   (list -96.0498 -175.862)
	   (list -96.0408 -175.864)
	   (list -96.0318 -175.862)
	   (list -96.0228 -175.857)
	   (list -96.0138 -175.85)
	   (list -96.0088 -175.845)
	   (list -96.0038 -175.84)
	   (list -95.9988 -175.834)
	   (list -95.9938 -175.827)
	   (list -95.8248 -175.627)
	   (list -95.8358 -175.618)
	   (list -95.8448 -175.611)
	   (list -95.8548 -175.603)
	   (list -95.8648 -175.595)
	   (list -95.8758 -175.588)
	   (list -95.8868 -175.582)
	   (list -95.8998 -175.577)
	   (list -95.9128 -175.572)
	   (list -95.9278 -175.57)
	   (list -95.9348 -175.569)
	   (list -95.9428 -175.568)
	   (list -95.9498 -175.569)
	   (list -95.9588 -175.57)
	   (list -95.9668 -175.571)
	   (list -95.9758 -175.573)
	   (list -95.9848 -175.576)
	   (list -95.9938 -175.579)
	   (list -96.0028 -175.583)
	   (list -96.0128 -175.588)
	   (list -96.0228 -175.594)
	   (list -96.0328 -175.6)
	   (list -96.0438 -175.608)
	   (list -96.0548 -175.616)
	   (list -96.0658 -175.625)
	   (list -96.0778 -175.636)
	   (list -96.0978 -175.619)
	   (list -95.8518 -175.325)
	   (list -95.8308 -175.342)
	   (list -95.8398 -175.355)
	   (list -95.8468 -175.368)
	   (list -95.8528 -175.38)
	   (list -95.8578 -175.392)
	   (list -95.8628 -175.404)
	   (list -95.8668 -175.414)
	   (list -95.8698 -175.425)
	   (list -95.8718 -175.435)
	   (list -95.8738 -175.445)
	   (list -95.8748 -175.454)
	   (list -95.8758 -175.463)
	   (list -95.8758 -175.472)
	   (list -95.8748 -175.48)
	   (list -95.8738 -175.488)
	   (list -95.8728 -175.496)
	   (list -95.8708 -175.503)
	   (list -95.8658 -175.516)
	   (list -95.8588 -175.529)
	   (list -95.8518 -175.54)
	   (list -95.8438 -175.551)
	   (list -95.8348 -175.56)
	   (list -95.8258 -175.569)
	   (list -95.8168 -175.577)
	   (list -95.8078 -175.585)
	   (list -95.7968 -175.593)
	   (list -95.6268 -175.39)
	   (list -95.6198 -175.382)
	   (list -95.6138 -175.374)
	   (list -95.6088 -175.367)
	   (list -95.6048 -175.361)
	   (list -95.6018 -175.354)
	   (list -95.5998 -175.347)
	   (list -95.5988 -175.341)
	   (list -95.5988 -175.334)
	   (list -95.6008 -175.327)
	   (list -95.6048 -175.32)
	   (list -95.6098 -175.312)
	   (list -95.6158 -175.303)
	   (list -95.6208 -175.298)
	   (list -95.6248 -175.294)
	   (list -95.6298 -175.289)
	   (list -95.6348 -175.284)
	   (list -95.6408 -175.278)
	   (list -95.6478 -175.272)
	   (list -95.6538 -175.266)
	   (list -95.6618 -175.26)
	   (list -95.6708 -175.253)
	   (list -95.6798 -175.246)
	   (list -95.6878 -175.239)
	   (list -95.6968 -175.233)
	   (list -95.7068 -175.227)
	   (list -95.7158 -175.221)
	   (list -95.7248 -175.216)
	   (list -95.7338 -175.211)
	   (list -95.7438 -175.206)
	   (list -95.7538 -175.202)
	   (list -95.7638 -175.199)
	   (list -95.7738 -175.196)
	   (list -95.7838 -175.193)
	   (list -95.7948 -175.191)
	   (list -95.8048 -175.189)
	   (list -95.8158 -175.188)
	   (list -95.8298 -175.187)
	   (list -95.8428 -175.186)
	   (list -95.8558 -175.186)
	   (list -95.8678 -175.187)
	   (list -95.8808 -175.188)
	   (list -95.8918 -175.19)
	   (list -95.9038 -175.192)
	   (list -95.9158 -175.194)
	   (list -95.9278 -175.197)
	   (list -95.9388 -175.201)
	   (list -95.9508 -175.204)
	   (list -95.9638 -175.209)
	   (list -95.9758 -175.213)
	   (list -95.9888 -175.219)
	   (list -96.0018 -175.224)
	   (list -96.0158 -175.231)
	   (list -96.0398 -175.211)
	   (list -95.8488 -175.062)
	   (list -95.8718 -175.072)
	   (list -95.8938 -175.084)
	   (list -95.8998 -175.074)
	   (list -95.9068 -175.066)
	   (list -95.9138 -175.058)
	   (list -95.9218 -175.052)
	   (list -95.9288 -175.046)
	   (list -95.9378 -175.042)
	   (list -95.9458 -175.039)
	   (list -95.9538 -175.036)
	   (list -95.9628 -175.035)
	   (list -95.9708 -175.035)
	   (list -95.9798 -175.035)
	   (list -95.9878 -175.036)
	   (list -95.9958 -175.038)
	   (list -96.0038 -175.041)
	   (list -96.0118 -175.044)
	   (list -96.0198 -175.048)
	   (list -96.5038 -175.327)
	   (list -96.5098 -175.331)
	   (list -96.5158 -175.336)
	   (list -96.5208 -175.341)
	   (list -96.5258 -175.348)
	   (list -96.5298 -175.354)
	   (list -96.5338 -175.362)
	   (list -96.5368 -175.37)
	   (list -96.5398 -175.378)
	   (list -96.5418 -175.386)
	   (list -96.5428 -175.395)
	   (list -96.5428 -175.404)
	   (list -96.5418 -175.413)
	   (list -96.5398 -175.423)
	   (list -96.5378 -175.432)
	   (list -96.5338 -175.441)
	   (list -96.5288 -175.451)
	   (list -96.5508 -175.463)
	   (list -96.7408 -175.133)
	   (list -96.7458 -175.124)
	   (list -96.7518 -175.114)
	   (list -96.7568 -175.104)
	   (list -96.7618 -175.093)
	   (list -96.7668 -175.082)
	   (list -96.7708 -175.071)
	   (list -96.7758 -175.059)
	   (list -96.7798 -175.048)
	   (list -96.7838 -175.035)
	   (list -96.7878 -175.023)
	   (list -96.7908 -175.011)
	   (list -96.7938 -174.998)
	   (list -96.7958 -174.985)
	   (list -96.7978 -174.973)
	   (list -96.7998 -174.96)
	   (list -96.8008 -174.947)
	   (list -96.8008 -174.934)
	   (list -96.8008 -174.922)
	   (list -96.7998 -174.909)
	   (list -96.7978 -174.897)
	   (list -96.7958 -174.885)
	   (list -96.7928 -174.873)
	   (list -96.7888 -174.861)
	   (list -96.7838 -174.85)
	   (list -96.7788 -174.839)
	   (list -96.7728 -174.828)
	   (list -96.7648 -174.818)
	   (list -96.7568 -174.808)
	   (list -96.7478 -174.798)
	   (list -96.7378 -174.789)
	   (list -96.7258 -174.781)
	   (list -96.7138 -174.773)
	   (list -96.7038 -174.768)
	   (list -96.6938 -174.763)
	   (list -96.6838 -174.759)
	   (list -96.6748 -174.756)
	   (list -96.6648 -174.753)
	   (list -96.6548 -174.751)
	   (list -96.6458 -174.749)
	   (list -96.6368 -174.748)
	   (list -96.6278 -174.748)
	   (list -96.6188 -174.748)
	   (list -96.6098 -174.748)
	   (list -96.6008 -174.749)
	   (list -96.5918 -174.751)
	   (list -96.5828 -174.753)
	   (list -96.5748 -174.755)
	   (list -96.5668 -174.758)
	   (list -96.5508 -174.764)
	   (list -96.5348 -174.772)
	   (list -96.5198 -174.781)
	   (list -96.5048 -174.791)
	   (list -96.4918 -174.802)
	   (list -96.4778 -174.813)
	   (list -96.4658 -174.825)
	   (list -96.4538 -174.837)
	   (list -96.2808 -174.473)
	   (list -96.2778 -174.466)
	   (list -96.2748 -174.459)
	   (list -96.2738 -174.452)
	   (list -96.2728 -174.445)
	   (list -96.2728 -174.438)
	   (list -96.2738 -174.431)
	   (list -96.2758 -174.423)
	   (list -96.2798 -174.415)
	   (list -96.2588 -174.403)
	   (list -96.2958 -174.258)
	   (list -96.2958 -174.488)
	   (list -96.3208 -174.488)
	   (list -96.3218 -174.478)
	   (list -96.3228 -174.469)
	   (list -96.3248 -174.46)
	   (list -96.3278 -174.451)
	   (list -96.3308 -174.443)
	   (list -96.3348 -174.435)
	   (list -96.3398 -174.428)
	   (list -96.3448 -174.422)
	   (list -96.3508 -174.416)
	   (list -96.3578 -174.411)
	   (list -96.3648 -174.407)
	   (list -96.3728 -174.403)
	   (list -96.3808 -174.4)
	   (list -96.3888 -174.398)
	   (list -96.3978 -174.396)
	   (list -96.4068 -174.396)
	   (list -96.9718 -174.396)
	   (list -96.9818 -174.396)
	   (list -96.9908 -174.397)
	   (list -96.9998 -174.398)
	   (list -97.0078 -174.401)
	   (list -97.0148 -174.403)
	   (list -97.0218 -174.407)
	   (list -97.0278 -174.411)
	   (list -97.0328 -174.417)
	   (list -97.0378 -174.423)
	   (list -97.0428 -174.431)
	   (list -97.0458 -174.439)
	   (list -97.0498 -174.449)
	   (list -97.0518 -174.459)
	   (list -97.0538 -174.471)
	   (list -97.0548 -174.485)
	   (list -97.0548 -174.5)
	   (list -97.0798 -174.5)
	   (list -97.0798 -174.207)
	   (list -96.5438 -173.988)
	   (list -97.0798 -173.757)
	   (list -97.0798 -173.469)
	   (list -97.0548 -173.469)
	   (list -97.0538 -173.482)
	   (list -97.0518 -173.495)
	   (list -97.0498 -173.506)
	   (list -97.0458 -173.515)
	   (list -97.0408 -173.524)
	   (list -97.0348 -173.532)
	   (list -97.0288 -173.539)
	   (list -97.0218 -173.544)
	   (list -97.0148 -173.549)
	   (list -97.0078 -173.553)
	   (list -96.9998 -173.556)
	   (list -96.9918 -173.559)
	   (list -96.9848 -173.561)
	   (list -96.9768 -173.562)
	   (list -96.9698 -173.563)
	   (list -96.9628 -173.563)
	   (list -96.4118 -173.563)
	   (list -96.4058 -173.563)
	   (list -96.3988 -173.562)
	   (list -96.3918 -173.561)
	   (list -96.3838 -173.559)
	   (list -96.3768 -173.557)
	   (list -96.3688 -173.554)
	   (list -96.3618 -173.55)
	   (list -96.3548 -173.545)
	   (list -96.3478 -173.54)
	   (list -96.3418 -173.533)
	   (list -96.3358 -173.525)
	   (list -96.3308 -173.516)
	   (list -96.3268 -173.507)
	   (list -96.3238 -173.495)
	   (list -96.3218 -173.483)
	   (list -96.3208 -173.469)
	   (list -96.2958 -173.469)
	   (list -96.2798 -173.527)
	   (list -96.2748 -173.519)
	   (list -96.2708 -173.51)
	   (list -96.2678 -173.502)
	   (list -96.2668 -173.493)
	   (list -96.2658 -173.485)
	   (list -96.2658 -173.477)
	   (list -96.2678 -173.468)
	   (list -96.2698 -173.46)
	   (list -96.2718 -173.452)
	   (list -96.2748 -173.444)
	   (list -96.2788 -173.436)
	   (list -96.2828 -173.428)
	   (list -96.2928 -173.412)
	   (list -96.3018 -173.397)
	   (list -96.6908 -172.791)
	   (list -96.6698 -172.762)
	   (list -95.9398 -172.923)
	   (list -95.9318 -172.925)
	   (list -95.9238 -172.926)
	   (list -95.9158 -172.928)
	   (list -95.9088 -172.929)
	   (list -95.8948 -172.929)
	   (list -95.8818 -172.927)
	   (list -95.8758 -172.926)
	   (list -95.8688 -172.923)
	   (list -95.8638 -172.92)
	   (list -95.8578 -172.916)
	   (list -95.8518 -172.911)
	   (list -95.8458 -172.905)
	   (list -95.8398 -172.898)
	   (list -95.8338 -172.89)
	   (list -95.8838 -172.728)
	   (list -95.8648 -172.709)
	   (list -95.8508 -172.718)
	   (list -95.8378 -172.726)
	   (list -95.8238 -172.734)
	   (list -95.8108 -172.741)
	   (list -95.7978 -172.747)
	   (list -95.7848 -172.752)
	   (list -95.7718 -172.758)
	   (list -95.7598 -172.762)
	   (list -95.7478 -172.766)
	   (list -95.7348 -172.769)
	   (list -95.7228 -172.772)
	   (list -95.7118 -172.774)
	   (list -95.6998 -172.776)
	   (list -95.6888 -172.777)
	   (list -95.6778 -172.778)
	   (list -95.6668 -172.778)
	   (list -95.6568 -172.777)
	   (list -95.6468 -172.777)
	   (list -95.6368 -172.775)
	   (list -95.6268 -172.774)
	   (list -95.6178 -172.772)
	   (list -95.6078 -172.769)
	   (list -95.5998 -172.767)
	   (list -95.5908 -172.763)
	   (list -95.5828 -172.76)
	   (list -95.5748 -172.756)
	   (list -95.5668 -172.752)
	   (list -95.5598 -172.747)
	   (list -95.5528 -172.743)
	   (list -95.5468 -172.737)
	   (list -95.5408 -172.732)
	   (list -95.5348 -172.727)
	   (list -95.5228 -172.715)
	   (list -95.5128 -172.702)
	   (list -95.5028 -172.689)
	   (list -95.4948 -172.676)
	   (list -95.4888 -172.664)
	   (list -95.4838 -172.651)
	   (list -95.4798 -172.638)
	   (list -95.4768 -172.624)
	   (list -95.4758 -172.612)
	   (list -95.4768 -172.599)
	   (list -95.4788 -172.586)
	   (list -95.4828 -172.573)
	   (list -95.4888 -172.561)
	   (list -95.4958 -172.548)
	   (list -95.4998 -172.542)
	   (list -95.5048 -172.536)
	   (list -95.5098 -172.53)
	   (list -95.5158 -172.525)
	   (list -95.5268 -172.515)
	   (list -95.5378 -172.507)
	   (list -95.5488 -172.501)
	   (list -95.5608 -172.497)
	   (list -95.5728 -172.494)
	   (list -95.5848 -172.493)
	   (list -95.5978 -172.493)
	   (list -95.6098 -172.493)
	   (list -95.6218 -172.495)
	   (list -95.6338 -172.497)
	   (list -95.6458 -172.5)
	   (list -95.6578 -172.504)
	   (list -95.6698 -172.507)
	   (list -95.6818 -172.511)
	   (list -95.6928 -172.515)
	   (list -95.7038 -172.518)
	   (list -95.8328 -172.559)
	   (list -95.8468 -172.563)
	   (list -95.8618 -172.566)
	   (list -95.8778 -172.569)
	   (list -95.8948 -172.57)
	   (list -95.9118 -172.571)
	   (list -95.9288 -172.571)
	   (list -95.9458 -172.57)
	   (list -95.9638 -172.568)
	   (list -95.9808 -172.565)
	   (list -95.9978 -172.561)
	   (list -96.0138 -172.555)
	   (list -96.0308 -172.549)
	   (list -96.0458 -172.541)
	   (list -96.0608 -172.532)
	   (list -96.0748 -172.522)
	   (list -96.0868 -172.511)
	   (list -96.0948 -172.503)
	   (list -96.1028 -172.494)
	   (list -96.1098 -172.486)
	   (list -96.1158 -172.476)
	   (list -96.1228 -172.467)
	   (list -96.1288 -172.458)
	   (list -96.1338 -172.448)
	   (list -96.1398 -172.438)
	   (list -96.1438 -172.428)
	   (list -96.1478 -172.418)
	   (list -96.1518 -172.408)
	   (list -96.1548 -172.397)
	   (list -96.1578 -172.386)
	   (list -96.1608 -172.376)
	   (list -96.1618 -172.365)
	   (list -96.1628 -172.354)
	   (list -96.1638 -172.343)
	   (list -96.1638 -172.332)
	   (list -96.1628 -172.321)
	   (list -96.1618 -172.31)
	   (list -96.1598 -172.299)
	   (list -96.1578 -172.288)
	   (list -96.1548 -172.277)
	   (list -96.1508 -172.266)
	   (list -96.1468 -172.255)
	   (list -96.1418 -172.244)
	   (list -96.1358 -172.233)
	   (list -96.1288 -172.223)
	   (list -96.1218 -172.212)
	   (list -96.1138 -172.202)
	   (list -96.1048 -172.192)
	   (list -96.0958 -172.182)
	   (list -96.0838 -172.17)
	   (list -96.0708 -172.16)
	   (list -96.0588 -172.15)
	   (list -96.0458 -172.141)
	   (list -96.0338 -172.133)
	   (list -96.0218 -172.126)
	   (list -96.0098 -172.119)
	   (list -95.9978 -172.112)
	   (list -95.9868 -172.106)
	   (list -95.9758 -172.101)
	   (list -95.9658 -172.095)
	   (list -95.9558 -172.09)
	   (list -95.9468 -172.084)
	   (list -95.9378 -172.078)
	   (list -95.9308 -172.072)
	   (list -95.9238 -172.066)
	   (list -95.9198 -172.062)
	   (list -95.9178 -172.056)
	   (list -95.9178 -172.05)
	   (list -95.9188 -172.043)
	   (list -95.9198 -172.036)
	   (list -95.9228 -172.029)
	   (list -95.9258 -172.022)
	   (list -95.9288 -172.014)
	   (list -95.9108 -171.995)
	   (list -95.5378 -171.857)
	   (list -95.1778 -171.76)
	   (list -95.1708 -171.784)
	   (list -95.1818 -171.788)
	   (list -95.1918 -171.792)
	   (list -95.1998 -171.796)
	   (list -95.2078 -171.802)
	   (list -95.2148 -171.808)
	   (list -95.2218 -171.814)
	   (list -95.2268 -171.821)
	   (list -95.2318 -171.828)
	   (list -95.2358 -171.836)
	   (list -95.2388 -171.843)
	   (list -95.2408 -171.852)
	   (list -95.2428 -171.86)
	   (list -95.2428 -171.868)
	   (list -95.2428 -171.876)
	   (list -95.2418 -171.885)
	   (list -95.2398 -171.893)
	   (list -95.1708 -172.153)
	   (list -94.9958 -171.847)
	   (list -94.9858 -171.83)
	   (list -94.9778 -171.813)
	   (list -94.9738 -171.805)
	   (list -94.9718 -171.797)
	   (list -94.9718 -171.789)
	   (list -94.9728 -171.781)
	   (list -94.9748 -171.776)
	   (list -94.9778 -171.771)
	   (list -94.9808 -171.767)
	   (list -94.9858 -171.764)
	   (list -94.9968 -171.758)
	   (list -95.0098 -171.754)
	   (list -95.0248 -171.753)
	   (list -95.0398 -171.753)
	   (list -95.0558 -171.754)
	   (list -95.0708 -171.757)
	   (list -95.0778 -171.734)
	   (list -94.7558 -171.647)
	   (list -94.7488 -171.671)
	   (list -94.7628 -171.675)
	   (list -94.7768 -171.68)
	   (list -94.7898 -171.684)
	   (list -94.8018 -171.689)
	   (list -94.8128 -171.695)
	   (list -94.8238 -171.701)
	   (list -94.8348 -171.708)
	   (list -94.8448 -171.715)
	   (list -94.8548 -171.722)
	   (list -94.8638 -171.731)
	   (list -94.8728 -171.74)
	   (list -94.8818 -171.75)
	   (list -94.8908 -171.761)
	   (list -94.8988 -171.774)
	   (list -94.9078 -171.786)
	   (list -94.9158 -171.8)
	   (list -95.0438 -172.023)
	   (list -94.6048 -172.346)
	   (list -94.5978 -172.351)
	   (list -94.5898 -172.356)
	   (list -94.5808 -172.361)
	   (list -94.5708 -172.366)
	   (list -94.5598 -172.37)
	   (list -94.5488 -172.372)
	   (list -94.5368 -172.373)
	   (list -94.5248 -172.371)
	   (list -94.5188 -172.395)
	   (list -94.8968 -172.496)
	   (list -94.9038 -172.472)
	   (list -94.8938 -172.469)
	   (list -94.8848 -172.466)
	   (list -94.8758 -172.463)
	   (list -94.8678 -172.46)
	   (list -94.8608 -172.457)
	   (list -94.8548 -172.454)
	   (list -94.8488 -172.45)
	   (list -94.8438 -172.446)
	   (list -94.8368 -172.439)
	   (list -94.8318 -172.43)
	   (list -94.8298 -172.421)
	   (list -94.8308 -172.412)
	   (list -94.8338 -172.407)
	   (list -94.8378 -172.402)
	   (list -94.8428 -172.396)
	   (list -94.8498 -172.391)
	   (list -94.8638 -172.381)
	   (list -94.8758 -172.372)
	   (list -95.1318 -172.178)
	   (list -95.1538 -172.215)
	   (list -95.0958 -172.43)
	   (list -95.0938 -172.439)
	   (list -95.0898 -172.447)
	   (list -95.0858 -172.455)
	   (list -95.0808 -172.463)
	   (list -95.0758 -172.469)
	   (list -95.0698 -172.476)
	   (list -95.0638 -172.481)
	   (list -95.0568 -172.486)
	   (list -95.0488 -172.49)
	   (list -95.0408 -172.493)
	   (list -95.0318 -172.496)
	   (list -95.0228 -172.497)
	   (list -95.0128 -172.498)
	   (list -95.0028 -172.497)
	   (list -94.9928 -172.496)
	   (list -94.9818 -172.493)
	   (list -94.9748 -172.517)
	   (list -95.3358 -172.614)
	   (list -95.3418 -172.59)
	   (list -95.3288 -172.586)
	   (list -95.3178 -172.581)
	   (list -95.3078 -172.575)
	   (list -95.2988 -172.568)
	   (list -95.2918 -172.561)
	   (list -95.2858 -172.554)
	   (list -95.2808 -172.546)
	   (list -95.2768 -172.538)
	   (list -95.2748 -172.53)
	   (list -95.2728 -172.522)
	   (list -95.2718 -172.513)
	   (list -95.2708 -172.506)
	   (list -95.2708 -172.498)
	   (list -95.2718 -172.49)
	   (list -95.2728 -172.484)
	   (list -95.2748 -172.478)
	   (list -95.4178 -171.941)
	   (list -95.4208 -171.933)
	   (list -95.4238 -171.925)
	   (list -95.4278 -171.918)
	   (list -95.4328 -171.911)
	   (list -95.4378 -171.904)
	   (list -95.4438 -171.898)
	   (list -95.4508 -171.893)
	   (list -95.4578 -171.888)
	   (list -95.4658 -171.885)
	   (list -95.4738 -171.881)
	   (list -95.4828 -171.879)
	   (list -95.4918 -171.878)
	   (list -95.5008 -171.877)
	   (list -95.5108 -171.877)
	   (list -95.5208 -171.879)
	   (list -95.5318 -171.881)
	   (list -95.5378 -171.857)
	   (list -95.9108 -171.995)
	   (list -95.7308 -172.172)
	   (list -95.7478 -172.19)
	   (list -95.7578 -172.186)
	   (list -95.7678 -172.181)
	   (list -95.7778 -172.176)
	   (list -95.7878 -172.172)
	   (list -95.7978 -172.168)
	   (list -95.8078 -172.164)
	   (list -95.8278 -172.157)
	   (list -95.8388 -172.154)
	   (list -95.8488 -172.151)
	   (list -95.8588 -172.149)
	   (list -95.8688 -172.147)
	   (list -95.8788 -172.144)
	   (list -95.8888 -172.143)
	   (list -95.8998 -172.142)
	   (list -95.9098 -172.141)
	   (list -95.9198 -172.141)
	   (list -95.9298 -172.141)
	   (list -95.9398 -172.142)
	   (list -95.9498 -172.143)
	   (list -95.9598 -172.144)
	   (list -95.9698 -172.146)
	   (list -95.9788 -172.149)
	   (list -95.9888 -172.152)
	   (list -95.9978 -172.156)
	   (list -96.0078 -172.16)
	   (list -96.0168 -172.165)
	   (list -96.0258 -172.171)
	   (list -96.0348 -172.177)
	   (list -96.0438 -172.184)
	   (list -96.0528 -172.191)
	   (list -96.0618 -172.2)
	   (list -96.0698 -172.209)
	   (list -96.0768 -172.218)
	   (list -96.0838 -172.228)
	   (list -96.0888 -172.239)
	   (list -96.0928 -172.249)
	   (list -96.0958 -172.26)
	   (list -96.0978 -172.271)
	   (list -96.0988 -172.282)
	   (list -96.0978 -172.293)
	   (list -96.0968 -172.305)
	   (list -96.0938 -172.316)
	   (list -96.0898 -172.327)
	   (list -96.0838 -172.338)
	   (list -96.0778 -172.348)
	   (list -96.0698 -172.358)
	   (list -96.0608 -172.368)
	   (list -96.0508 -172.377)
	   (list -96.0418 -172.384)
	   (list -96.0318 -172.389)
	   (list -96.0208 -172.394)
	   (list -96.0098 -172.397)
	   (list -95.9988 -172.399)
	   (list -95.9868 -172.4)
	   (list -95.9748 -172.4)
	   (list -95.9628 -172.399)
	   (list -95.9508 -172.398)
	   (list -95.9378 -172.395)
	   (list -95.9248 -172.392)
	   (list -95.9118 -172.389)
	   (list -95.8978 -172.384)
	   (list -95.8848 -172.38)
	   (list -95.8708 -172.375)
	   (list -95.7688 -172.335)
	   (list -95.7608 -172.332)
	   (list -95.7498 -172.329)
	   (list -95.7438 -172.327)
	   (list -95.7378 -172.325)
	   (list -95.7308 -172.323)
	   (list -95.7228 -172.321)
	   (list -95.7148 -172.319)
	   (list -95.7068 -172.318)
	   (list -95.6978 -172.316)
	   (list -95.6898 -172.315)
	   (list -95.6798 -172.314)
	   (list -95.6708 -172.313)
	   (list -95.6608 -172.313)
	   (list -95.6508 -172.313)
	   (list -95.6398 -172.313)
	   (list -95.6298 -172.313)
	   (list -95.6188 -172.314)
	   (list -95.6088 -172.316)
	   (list -95.5978 -172.318)
	   (list -95.5868 -172.32)
	   (list -95.5758 -172.324)
	   (list -95.5648 -172.327)
	   (list -95.5538 -172.331)
	   (list -95.5428 -172.336)
	   (list -95.5318 -172.342)
	   (list -95.5208 -172.348)
	   (list -95.5098 -172.356)
	   (list -95.4998 -172.363)
	   (list -95.4888 -172.372)
	   (list -95.4788 -172.382)
	   (list -95.4708 -172.39)
	   (list -95.4638 -172.399)
	   (list -95.4568 -172.408)
	   (list -95.4498 -172.417)
	   (list -95.4438 -172.427)
	   (list -95.4378 -172.437)
	   (list -95.4328 -172.447)
	   (list -95.4288 -172.457)
	   (list -95.4238 -172.468)
	   (list -95.4208 -172.479)
	   (list -95.4178 -172.49)
	   (list -95.4148 -172.502)
	   (list -95.4128 -172.513)
	   (list -95.4118 -172.525)
	   (list -95.4108 -172.537)
	   (list -95.4108 -172.549)
	   (list -95.4118 -172.561)
	   (list -95.4128 -172.573)
	   (list -95.4138 -172.585)
	   (list -95.4168 -172.597)
	   (list -95.4198 -172.61)
	   (list -95.4238 -172.622)
	   (list -95.4278 -172.634)
	   (list -95.4328 -172.646)
	   (list -95.4388 -172.659)
	   (list -95.4448 -172.671)
	   (list -95.4528 -172.683)
	   (list -95.4608 -172.695)
	   (list -95.4698 -172.708)
	   (list -95.4788 -172.719)
	   (list -95.4888 -172.731)
	   (list -95.5008 -172.743)
	   (list -95.5108 -172.753)
	   (list -95.5218 -172.762)
	   (list -95.5338 -172.771)
	   (list -95.5458 -172.779)
	   (list -95.5568 -172.787)
	   (list -95.5688 -172.795)
	   (list -95.5818 -172.802)
	   (list -95.5938 -172.809)
	   (list -95.6048 -172.816)
	   (list -95.6168 -172.822)
	   (list -95.6268 -172.829)
	   (list -95.6378 -172.835)
	   (list -95.6468 -172.841)
	   (list -95.6548 -172.846)
	   (list -95.6628 -172.852)
	   (list -95.6688 -172.858)
	   (list -95.6728 -172.862)
	   (list -95.6758 -172.866)
	   (list -95.6788 -172.87)
	   (list -95.6798 -172.874)
	   (list -95.6818 -172.881)
	   (list -95.6808 -172.887)
	   (list -95.6748 -172.898)
	   (list -95.6668 -172.908)
	   (list -95.6848 -172.926)
	   (list -95.8838 -172.728)
	   (list -95.8338 -172.89)
	   (list -95.8138 -172.905)
	   (list -96.0248 -173.207)
	   (list -96.0458 -173.192)
	   (list -96.0378 -173.181)
	   (list -96.0308 -173.17)
	   (list -96.0248 -173.159)
	   (list -96.0208 -173.15)
	   (list -96.0168 -173.141)
	   (list -96.0138 -173.133)
	   (list -96.0118 -173.125)
	   (list -96.0108 -173.118)
	   (list -96.0108 -173.111)
	   (list -96.0108 -173.105)
	   (list -96.0118 -173.1)
	   (list -96.0138 -173.095)
	   (list -96.0188 -173.086)
	   (list -96.0268 -173.08)
	   (list -96.0328 -173.076)
	   (list -96.0408 -173.072)
	   (list -96.0488 -173.07)
	   (list -96.0568 -173.069)
	   (list -96.1828 -173.042)
	   (list -96.3348 -173.26)
	   (list -96.2678 -173.358)
	   (list -96.2648 -173.363)
	   (list -96.2608 -173.368)
	   (list -96.2558 -173.373)
	   (list -96.2498 -173.377)
	   (list -96.2398 -173.382)
	   (list -96.2298 -173.386)
	   (list -96.2238 -173.387)
	   (list -96.2178 -173.388)
	   (list -96.2118 -173.387)
	   (list -96.2058 -173.386)
	   (list -96.1988 -173.384)
	   (list -96.1918 -173.381)
	   (list -96.1848 -173.377)
	   (list -96.1778 -173.372)
	   (list -96.1708 -173.366)
	   (list -96.1628 -173.358)
	   (list -96.1558 -173.349)
	   (list -96.1478 -173.339)
	   (list -96.1278 -173.353)
	   (list -96.2598 -173.541)
	   (list -96.2798 -173.527)
	   (list -96.2958 -173.469)
	   (list -96.2958 -173.842)
	   (list -96.3208 -173.842)
	   (list -96.3218 -173.829)
	   (list -96.3238 -173.817)
	   (list -96.3268 -173.807)
	   (list -96.3308 -173.797)
	   (list -96.3358 -173.788)
	   (list -96.3408 -173.781)
	   (list -96.3468 -173.774)
	   (list -96.3538 -173.768)
	   (list -96.3608 -173.763)
	   (list -96.3688 -173.758)
	   (list -96.3758 -173.755)
	   (list -96.3838 -173.752)
	   (list -96.3908 -173.75)
	   (list -96.3978 -173.748)
	   (list -96.4048 -173.748)
	   (list -96.4118 -173.747)
	   (list -96.9778 -173.747)
	   (list -96.2958 -174.04)
	   (list -96.2958 -174.068)
	   (list -96.9798 -174.351)
	   (list -96.4098 -174.351)
	   (list -96.3938 -174.349)
	   (list -96.3778 -174.345)
	   (list -96.3698 -174.342)
	   (list -96.3628 -174.338)
	   (list -96.3558 -174.334)
	   (list -96.3488 -174.329)
	   (list -96.3428 -174.322)
	   (list -96.3378 -174.316)
	   (list -96.3328 -174.308)
	   (list -96.3288 -174.3)
	   (list -96.3258 -174.291)
	   (list -96.3228 -174.28)
	   (list -96.3218 -174.269)
	   (list -96.3208 -174.258)
	   (list -96.2958 -174.258)
	   (list -96.2588 -174.403)
	   (list -96.1448 -174.599)
	   (list -96.3418 -174.988)
	   (list -96.3278 -175.013)
	   (list -96.1118 -174.888)
	   (list -96.1068 -174.885)
	   (list -96.1018 -174.881)
	   (list -96.0958 -174.877)
	   (list -96.0908 -174.872)
	   (list -96.0858 -174.866)
	   (list -96.0808 -174.859)
	   (list -96.0758 -174.852)
	   (list -96.0718 -174.844)
	   (list -96.0688 -174.836)
	   (list -96.0668 -174.827)
	   (list -96.0648 -174.817)
	   (list -96.0648 -174.807)
	   (list -96.0668 -174.796)
	   (list -96.0698 -174.785)
	   (list -96.0738 -174.773)
	   (list -96.0798 -174.761)
	   (list -96.0588 -174.749)
	   (list -95.8718 -175.072)
	   (list -95.8488 -175.062)
	   (list -95.3428 -175.486)
	   (list -95.2968 -175.496)
	   (list -94.9398 -175.605)
	   (list -94.9478 -175.628)
	   (list -94.9578 -175.625)
	   (list -94.9678 -175.624)
	   (list -94.9778 -175.623)
	   (list -94.9878 -175.623)
	   (list -94.9968 -175.624)
	   (list -95.0058 -175.626)
	   (list -95.0138 -175.629)
	   (list -95.0218 -175.633)
	   (list -95.0298 -175.637)
	   (list -95.0368 -175.643)
	   (list -95.0428 -175.649)
	   (list -95.0478 -175.655)
	   (list -95.0538 -175.662)
	   (list -95.0578 -175.67)
	   (list -95.0618 -175.678)
	   (list -95.0648 -175.687)
	   (list -95.2328 -176.218)
	   "c"
  )
  (command "pline"
	   (list -111.731 -173.172)
	   "w"
	   0
	   0
	   (list -111.731 -173.495)
	   (list -111.74 -173.754)
	   (list -111.74 -174.05)
	   (list -113.185 -174.05)
	   (list -113.185 -173.754)
	   (list -111.74 -173.754)
	   (list -111.731 -173.495)
	   (list -113.185 -173.495)
	   (list -113.185 -173.172)
	   (list -111.731 -173.172)
	   (list -112.191 -172.913)
	   (list -112.71 -172.913)
	   (list -112.71 -172.503)
	   (list -112.191 -172.503)
	   (list -112.185 -172.265)
	   (list -112.722 -172.256)
	   (list -112.713 -171.784)
	   (list -113.018 -171.793)
	   (list -113.027 -171.784)
	   (list -113.018 -172.237)
	   (list -113.657 -172.228)
	   (list -113.638 -172.515)
	   (list -113.009 -172.496)
	   (list -113.018 -172.922)
	   (list -113.499 -172.931)
	   (list -113.49 -174.309)
	   (list -112.648 -174.309)
	   (list -112.685 -174.689)
	   (list -113.685 -174.689)
	   (list -113.685 -174.975)
	   (list -112.768 -174.966)
	   (list -112.783 -175.001)
	   (list -112.8 -175.035)
	   (list -112.817 -175.069)
	   (list -112.836 -175.102)
	   (list -112.855 -175.134)
	   (list -112.876 -175.166)
	   (list -112.898 -175.197)
	   (list -112.921 -175.227)
	   (list -112.945 -175.257)
	   (list -112.97 -175.285)
	   (list -112.996 -175.313)
	   (list -113.023 -175.34)
	   (list -113.05 -175.366)
	   (list -113.079 -175.391)
	   (list -113.108 -175.415)
	   (list -113.138 -175.438)
	   (list -113.182 -175.469)
	   (list -113.226 -175.498)
	   (list -113.272 -175.526)
	   (list -113.318 -175.552)
	   (list -113.365 -175.577)
	   (list -113.414 -175.6)
	   (list -113.462 -175.622)
	   (list -113.512 -175.642)
	   (list -113.562 -175.66)
	   (list -113.613 -175.676)
	   (list -113.664 -175.691)
	   (list -113.716 -175.704)
	   (list -113.768 -175.715)
	   (list -113.736 -175.737)
	   (list -113.705 -175.759)
	   (list -113.674 -175.782)
	   (list -113.645 -175.807)
	   (list -113.616 -175.832)
	   (list -113.588 -175.858)
	   (list -113.561 -175.885)
	   (list -113.535 -175.913)
	   (list -113.51 -175.942)
	   (list -113.486 -175.972)
	   (list -113.462 -176.002)
	   (list -113.288 -175.892)
	   (list -113.117 -175.777)
	   (list -112.95 -175.656)
	   (list -112.787 -175.53)
	   (list -112.768 -175.515)
	   (list -112.75 -175.499)
	   (list -112.732 -175.482)
	   (list -112.715 -175.465)
	   (list -112.699 -175.447)
	   (list -112.683 -175.429)
	   (list -112.668 -175.41)
	   (list -112.653 -175.391)
	   (list -112.639 -175.371)
	   (list -112.626 -175.35)
	   (list -112.613 -175.33)
	   (list -112.601 -175.308)
	   (list -112.511 -175.134)
	   (list -112.426 -174.957)
	   (list -112.37 -174.966)
	   (list -112.334 -175.042)
	   (list -112.295 -175.117)
	   (list -112.253 -175.19)
	   (list -112.209 -175.262)
	   (list -112.163 -175.332)
	   (list -112.114 -175.4)
	   (list -112.063 -175.467)
	   (list -112.009 -175.532)
	   (list -111.953 -175.595)
	   (list -111.92 -175.63)
	   (list -111.886 -175.664)
	   (list -111.85 -175.697)
	   (list -111.814 -175.728)
	   (list -111.776 -175.759)
	   (list -111.737 -175.787)
	   (list -111.698 -175.815)
	   (list -111.657 -175.841)
	   (list -111.616 -175.866)
	   (list -111.574 -175.889)
	   (list -111.53 -175.911)
	   (list -111.487 -175.932)
	   (list -111.442 -175.951)
	   (list -111.397 -175.968)
	   (list -111.352 -175.984)
	   (list -111.32 -175.932)
	   (list -111.286 -175.882)
	   (list -111.25 -175.833)
	   (list -111.213 -175.786)
	   (list -111.175 -175.739)
	   (list -111.134 -175.694)
	   (list -111.092 -175.651)
	   (list -111.153 -175.63)
	   (list -111.213 -175.608)
	   (list -111.272 -175.584)
	   (list -111.33 -175.558)
	   (list -111.388 -175.53)
	   (list -111.444 -175.5)
	   (list -111.5 -175.468)
	   (list -111.554 -175.434)
	   (list -111.607 -175.399)
	   (list -111.659 -175.362)
	   (list -111.71 -175.323)
	   (list -111.759 -175.283)
	   (list -111.808 -175.241)
	   (list -111.854 -175.197)
	   (list -111.899 -175.152)
	   (list -111.943 -175.105)
	   (list -111.985 -175.057)
	   (list -112.026 -175.008)
	   (list -112.064 -174.957)
	   (list -111.213 -174.966)
	   (list -111.213 -174.689)
	   (list -112.361 -174.698)
	   (list -112.333 -174.309)
	   (list -111.426 -174.3)
	   (list -111.426 -172.931)
	   (list -111.907 -172.922)
	   (list -111.907 -172.496)
	   (list -111.231 -172.515)
	   (list -111.25 -172.237)
	   (list -111.898 -172.256)
	   (list -111.879 -171.803)
	   (list -112.213 -171.793)
	   (list -112.185 -172.265)
	   (list -112.191 -172.503)
	   (list -112.191 -172.913)
	   "c"
  )
  (command "pline"
	   (list -114.692 -173.361)
	   "w"
	   0
	   0
	   (list -114.185 -173.357)
	   (list -114.185 -174.134)
	   (list -114.689 -174.132)
	   (list -114.685 -174.41)
	   (list -114.194 -174.393)
	   (list -114.185 -175.336)
	   (list -114.296 -175.401)
	   (list -114.583 -175.392)
	   (list -114.481 -175.789)
	   (list -114.344 -175.765)
	   (list -114.208 -175.737)
	   (list -114.073 -175.706)
	   (list -114.065 -175.704)
	   (list -114.057 -175.702)
	   (list -114.049 -175.699)
	   (list -114.041 -175.696)
	   (list -114.034 -175.693)
	   (list -114.026 -175.689)
	   (list -114.019 -175.685)
	   (list -114.011 -175.681)
	   (list -114.004 -175.677)
	   (list -113.997 -175.673)
	   (list -113.99 -175.668)
	   (list -113.983 -175.663)
	   (list -113.977 -175.658)
	   (list -113.97 -175.652)
	   (list -113.964 -175.647)
	   (list -113.958 -175.641)
	   (list -113.952 -175.635)
	   (list -113.947 -175.628)
	   (list -113.942 -175.622)
	   (list -113.936 -175.615)
	   (list -113.932 -175.609)
	   (list -113.927 -175.602)
	   (list -113.922 -175.594)
	   (list -113.918 -175.587)
	   (list -113.914 -175.58)
	   (list -113.911 -175.572)
	   (list -113.907 -175.565)
	   (list -113.904 -175.557)
	   (list -113.901 -175.549)
	   (list -113.899 -175.541)
	   (list -113.896 -175.533)
	   (list -113.894 -175.525)
	   (list -113.893 -175.517)
	   (list -113.891 -175.508)
	   (list -113.89 -175.5)
	   (list -113.889 -175.492)
	   (list -113.889 -175.483)
	   (list -113.888 -175.475)
	   (list -113.87 -172.034)
	   (list -115.008 -172.025)
	   (list -114.99 -174.254)
	   (list -114.991 -174.34)
	   (list -114.994 -174.427)
	   (list -115.001 -174.513)
	   (list -115.01 -174.599)
	   (list -115.023 -174.685)
	   (list -115.038 -174.77)
	   (list -115.056 -174.855)
	   (list -115.077 -174.939)
	   (list -115.101 -175.022)
	   (list -115.127 -175.105)
	   (list -115.156 -175.186)
	   (list -115.188 -175.267)
	   (list -115.223 -175.346)
	   (list -115.261 -175.424)
	   (list -115.3 -175.501)
	   (list -115.343 -175.577)
	   (list -115.388 -175.651)
	   (list -115.055 -175.799)
	   (list -115.006 -175.704)
	   (list -114.961 -175.607)
	   (list -114.919 -175.509)
	   (list -114.88 -175.41)
	   (list -114.845 -175.309)
	   (list -114.813 -175.207)
	   (list -114.785 -175.104)
	   (list -114.76 -175.0)
	   (list -114.739 -174.896)
	   (list -114.721 -174.79)
	   (list -114.708 -174.694)
	   (list -114.698 -174.597)
	   (list -114.69 -174.499)
	   (list -114.684 -174.402)
	   (list -114.703 -172.302)
	   (list -114.185 -172.302)
	   (list -114.185 -173.079)
	   (list -114.699 -173.076)
	   "c"
  )
  (command "pline"
	   (list -107.848 -175.327)
	   "w"
	   0
	   0
	   (list -108.21 -175.327)
	   (list -108.969 -175.327)
	   (list -108.969 -174.744)
	   (list -108.21 -174.744)
	   (list -108.191 -174.476)
	   (list -108.959 -174.476)
	   (list -108.959 -173.995)
	   (list -108.191 -173.995)
	   (list -108.182 -173.708)
	   (list -108.969 -173.708)
	   (list -108.969 -173.209)
	   (list -109.293 -173.218)
	   (list -109.293 -175.345)
	   (list -109.904 -175.345)
	   (list -109.904 -173.218)
	   (list -109.293 -173.218)
	   (list -108.969 -173.209)
	   (list -108.182 -173.209)
	   (list -108.182 -173.708)
	   (list -108.191 -173.995)
	   (list -108.191 -174.476)
	   (list -108.21 -174.744)
	   (list -108.21 -175.327)
	   (list -107.848 -175.327)
	   (list -107.848 -173.209)
	   (list -107.247 -173.209)
	   (list -107.247 -175.327)
	   (list -107.256 -175.604)
	   (list -107.237 -175.873)
	   (list -106.886 -175.863)
	   (list -106.876 -172.931)
	   (list -108.487 -172.94)
	   (list -108.348 -172.311)
	   (list -106.515 -172.321)
	   (list -106.525 -172.006)
	   (list -110.626 -171.997)
	   (list -110.617 -172.006)
	   (list -110.626 -172.321)
	   (list -108.746 -172.311)
	   (list -108.867 -172.931)
	   (list -110.274 -172.931)
	   (list -110.274 -175.873)
	   (list -109.922 -175.882)
	   (list -109.913 -175.614)
	   (list -107.256 -175.604)
	   (list -107.247 -175.327)
	   "c"
  )
  (command "pline"
	   (list -95.4578 -176.217)
	   "w"
	   0
	   0
	   (list -95.4648 -176.217)
	   (list -95.4708 -176.216)
	   (list -95.4778 -176.214)
	   (list -95.4858 -176.212)
	   (list -95.4938 -176.21)
	   (list -95.5018 -176.207)
	   (list -95.5128 -176.203)
	   (list -95.5238 -176.197)
	   (list -95.5338 -176.19)
	   (list -95.5428 -176.182)
	   (list -95.5508 -176.172)
	   (list -95.5578 -176.162)
	   (list -95.5638 -176.15)
	   (list -95.5688 -176.138)
	   (list -95.5728 -176.124)
	   (list -95.5758 -176.11)
	   (list -95.5768 -176.094)
	   (list -95.5778 -176.078)
	   (list -95.5768 -176.069)
	   (list -95.5758 -176.061)
	   (list -95.5748 -176.052)
	   (list -95.5738 -176.043)
	   (list -95.5718 -176.033)
	   (list -95.5698 -176.024)
	   (list -95.5668 -176.014)
	   (list -95.5638 -176.004)
	   (list -95.5588 -175.989)
	   (list -95.5528 -175.975)
	   (list -95.5468 -175.96)
	   (list -95.5388 -175.946)
	   (list -95.5308 -175.932)
	   (list -95.5208 -175.92)
	   (list -95.5098 -175.909)
	   (list -95.4978 -175.899)
	   (list -95.4918 -175.894)
	   (list -95.4848 -175.89)
	   (list -95.4778 -175.886)
	   (list -95.4698 -175.883)
	   (list -95.4618 -175.88)
	   (list -95.4528 -175.878)
	   (list -95.4438 -175.876)
	   (list -95.4348 -175.875)
	   (list -95.4258 -175.875)
	   (list -95.4148 -175.874)
	   (list -95.4048 -175.875)
	   (list -95.3938 -175.876)
	   (list -95.3818 -175.878)
	   (list -95.3698 -175.88)
	   (list -95.3568 -175.883)
	   (list -95.3438 -175.887)
	   (list -95.3238 -175.894)
	   (list -95.4148 -176.182)
	   (list -95.4178 -176.19)
	   (list -95.4208 -176.197)
	   (list -95.4238 -176.202)
	   (list -95.4278 -176.207)
	   (list -95.4368 -176.214)
	   (list -95.4468 -176.217)
	   (list -95.4518 -176.218)
	   "c"
  )
  (command "pline"
	   (list -96.6148 -174.933)
	   "w"
	   0
	   0
	   (list -96.6028 -174.926)
	   (list -96.5908 -174.92)
	   (list -96.5788 -174.915)
	   (list -96.5678 -174.91)
	   (list -96.5578 -174.906)
	   (list -96.5468 -174.903)
	   (list -96.5378 -174.901)
	   (list -96.5278 -174.899)
	   (list -96.5188 -174.898)
	   (list -96.5098 -174.897)
	   (list -96.5018 -174.898)
	   (list -96.4928 -174.899)
	   (list -96.4848 -174.9)
	   (list -96.4768 -174.902)
	   (list -96.4698 -174.905)
	   (list -96.4628 -174.908)
	   (list -96.4548 -174.913)
	   (list -96.4478 -174.917)
	   (list -96.4418 -174.922)
	   (list -96.4348 -174.927)
	   (list -96.4278 -174.934)
	   (list -96.4218 -174.94)
	   (list -96.4158 -174.947)
	   (list -96.4088 -174.955)
	   (list -96.4028 -174.963)
	   (list -96.3968 -174.971)
	   (list -96.3908 -174.98)
	   (list -96.3848 -174.99)
	   (list -96.3778 -174.999)
	   (list -96.3718 -175.01)
	   (list -96.3658 -175.02)
	   (list -96.3598 -175.031)
	   (list -96.6108 -175.176)
	   (list -96.6188 -175.18)
	   (list -96.6258 -175.183)
	   (list -96.6328 -175.184)
	   (list -96.6398 -175.184)
	   (list -96.6518 -175.182)
	   (list -96.6628 -175.176)
	   (list -96.6718 -175.169)
	   (list -96.6798 -175.16)
	   (list -96.6858 -175.152)
	   (list -96.6908 -175.144)
	   (list -96.6948 -175.136)
	   (list -96.6978 -175.129)
	   (list -96.7018 -175.121)
	   (list -96.7048 -175.114)
	   (list -96.7098 -175.1)
	   (list -96.7128 -175.085)
	   (list -96.7148 -175.071)
	   (list -96.7148 -175.058)
	   (list -96.7128 -175.044)
	   (list -96.7088 -175.031)
	   (list -96.7038 -175.018)
	   (list -96.6968 -175.005)
	   (list -96.6928 -174.999)
	   (list -96.6878 -174.992)
	   (list -96.6828 -174.986)
	   (list -96.6768 -174.98)
	   (list -96.6708 -174.974)
	   (list -96.6648 -174.968)
	   (list -96.6578 -174.962)
	   (list -96.6498 -174.956)
	   (list -96.6418 -174.95)
	   (list -96.6328 -174.944)
	   (list -96.6238 -174.939)
	   "c"
  )
  (command "pline"
	   (list -96.3618 -173.218)
	   "w"
	   0
	   0
	   (list -96.5308 -172.965)
	   (list -96.2308 -173.031)
	   "c"
  )
  (command "pline"
	   (list -94.0558 -174.954)
	   "w"
	   0
	   0
	   (list -93.7338 -175.275)
	   (list -93.6458 -175.512)
	   (list -92.9128 -176.1)
	   (list -92.2024 -176.755)
	   (list -91.9215 -174.062)
	   (list -94.5988 -174.38)
	   "c"
  )
  (command "pline"
	   (list -94.2258 -173.03)
	   "w"
	   0
	   0
	   (list -94.1788 -173.055)
	   (list -94.1328 -173.082)
	   (list -94.0888 -173.11)
	   (list -94.0448 -173.139)
	   (list -94.0018 -173.17)
	   (list -93.9608 -173.203)
	   (list -93.9198 -173.237)
	   (list -93.8808 -173.272)
	   (list -93.8428 -173.309)
	   (list -93.7648 -173.016)
	   (list -93.5778 -173.066)
	   (list -93.5228 -172.862)
	   (list -93.3228 -172.915)
	   (list -93.2668 -172.706)
	   (list -93.0708 -172.759)
	   (list -93.0208 -172.572)
	   (list -92.8208 -172.625)
	   (list -92.7643 -172.416)
	   (list -92.3969 -172.515)
	   (list -92.4729 -172.413)
	   (list -92.5522 -172.313)
	   (list -92.6346 -172.216)
	   (list -92.7201 -172.122)
	   (list -92.8088 -172.03)
	   (list -92.8468 -172.245)
	   (list -93.0088 -172.216)
	   (list -93.0438 -172.417)
	   (list -93.2278 -172.385)
	   (list -93.2618 -172.577)
	   (list -93.4408 -172.545)
	   (list -93.4708 -172.717)
	   (list -93.6548 -172.684)
	   (list -93.6888 -172.876)
	   (list -93.8608 -172.846)
	   (list -93.8938 -173.034)
	   (list -94.2048 -172.979)
	   "c"
  )
  (command "pline"
	   (list -93.1638 -173.155)
	   "w"
	   0
	   0
	   (list -93.2468 -173.381)
	   (list -93.4488 -173.308)
	   (list -93.5298 -173.529)
	   (list -93.7348 -173.454)
	   (list -93.7168 -173.484)
	   (list -93.7008 -173.514)
	   (list -93.6848 -173.544)
	   (list -93.6698 -173.575)
	   (list -93.6558 -173.606)
	   (list -93.6428 -173.638)
	   (list -93.6308 -173.67)
	   (list -93.6198 -173.703)
	   (list -93.6108 -173.736)
	   (list -93.5898 -173.679)
	   (list -93.3628 -173.762)
	   (list -93.2718 -173.513)
	   (list -93.0278 -173.602)
	   (list -92.9358 -173.347)
	   (list -92.6976 -173.434)
	   (list -92.6149 -173.207)
	   (list -92.3715 -173.295)
	   (list -92.2789 -173.041)
	   (list -92.0997 -173.106)
	   (list -92.1298 -173.026)
	   (list -92.1624 -172.947)
	   (list -92.1974 -172.869)
	   (list -92.2349 -172.792)
	   (list -92.2748 -172.717)
	   (list -92.3641 -172.962)
	   (list -92.5805 -172.883)
	   (list -92.6628 -173.109)
	   (list -92.8748 -173.032)
	   (list -92.9478 -173.234)
	   "c"
  )
  (command "pline"
	   (list -93.1428 -173.79)
	   "w"
	   0
	   0
	   (list -93.3698 -173.707)
	   (list -93.4608 -173.956)
	   (list -93.5758 -173.914)
	   (list -93.5718 -173.951)
	   (list -93.5698 -173.989)
	   (list -93.5688 -174.026)
	   (list -93.5698 -174.063)
	   (list -93.5708 -174.1)
	   (list -93.5478 -174.052)
	   (list -93.3308 -174.153)
	   (list -93.3418 -174.177)
	   (list -93.1898 -174.159)
	   (list -93.2818 -174.116)
	   (list -93.1798 -173.899)
	   (list -92.9188 -174.02)
	   (list -92.7918 -173.748)
	   (list -92.5369 -173.867)
	   (list -92.4233 -173.623)
	   (list -92.1624 -173.745)
	   (list -92.0353 -173.472)
	   (list -91.9927 -173.492)
	   (list -92.0118 -173.404)
	   (list -92.0339 -173.317)
	   (list -92.0587 -173.23)
	   (list -92.0865 -173.144)
	   (list -92.1498 -173.318)
	   (list -92.3933 -173.229)
	   (list -92.4858 -173.484)
	   (list -92.7239 -173.397)
	   (list -92.8068 -173.624)
	   (list -93.0498 -173.536)
	   "c"
  )
  (command "pline"
	   (list -92.9368 -173.945)
	   "w"
	   0
	   0
	   (list -93.0268 -174.138)
	   (list -91.9403 -174.003)
	   (list -91.9419 -173.928)
	   (list -91.9457 -173.852)
	   (list -91.9516 -173.776)
	   (list -92.1802 -173.67)
	   (list -92.3072 -173.942)
	   (list -92.5623 -173.823)
	   (list -92.6759 -174.067)
	   "c"
  )
  (command "pline"
	   (list -93.8868 -173.163)
	   "w"
	   0
	   0
	   (list -93.9348 -173.216)
	   (list -93.9008 -173.251)
	   (list -93.8668 -173.288)
	   (list -93.8348 -173.325)
	   (list -93.8028 -173.363)
	   (list -93.7728 -173.402)
	   (list -93.7448 -173.443)
	   (list -93.7168 -173.484)
	   (list -93.6438 -173.283)
	   (list -93.4418 -173.357)
	   (list -93.3618 -173.135)
	   (list -93.1448 -173.214)
	   (list -93.0628 -172.988)
	   (list -92.8508 -173.065)
	   (list -92.7775 -172.863)
	   (list -92.5611 -172.942)
	   (list -92.4789 -172.716)
	   (list -92.2273 -172.807)
	   (list -92.2755 -172.719)
	   (list -92.3264 -172.632)
	   (list -92.3797 -172.547)
	   (list -92.4356 -172.463)
	   (list -92.4939 -172.381)
	   (list -92.5546 -172.301)
	   (list -92.6421 -172.628)
	   (list -92.8428 -172.574)
	   (list -92.8988 -172.783)
	   (list -93.0938 -172.731)
	   (list -93.1438 -172.918)
	   (list -93.3448 -172.864)
	   (list -93.4008 -173.073)
	   (list -93.5878 -173.023)
	   (list -93.6428 -173.228)
	   "c"
  )
  (command "style" "ht" "simhei.ttf" "" "" "" "" "" "")
  (setq c_date (rtos (getvar "CDATE")))
  (setq	c_date (strcat (substr c_date 1 4)
		       "/"
		       (substr c_date 5 2)
		       "/"
		       (substr c_date 7 2)
	       )
  )
  (setq	txt_dt (list (cons 0 "TEXT")
		     (cons 1 c_date)
		     (cons 10 (trans (list -85 -177 0) 1 0))
		     (cons 40 3)
		     (cons 7 "ht")
	       )
  )
  (entmake txt_dt)
)

(defun get_dt_vl (item dt)
  (cdr (assoc item dt))
)
(defun c:gdsinit ()
  (defun set_var ()
    (setq osnap_old (getvar "osmode"))
    (setq orthomode_old (getvar "orthomode"))
    (setvar "osmode" 0)
    (setvar "orthomode" 0)
    (list osnap_old orthomode_old)
  )

  (setq val_list (set_var))
  (command "layer" "T" "*" "U" "*" "LO"	"0" "LO" "000" "LO" "001" "LO"
	   "010" "")
  (command "erase" "ALL" "")
  (command "layer" "U" "*" "C" "white" "*" "")
  (command "scale" "ALL" "" "0,0" "0.1")
  (command "zoom" "e")
  (command "purge" "ALL" "*" "N")
  (setq pos_ss (ssget "x" (list (cons 0 "line") (cons 8 "0"))))
  (if pos_ss
    (progn
      (setq ss_ttl (sslength pos_ss))
      (setq cnt 0)
      (setq line_dt (entget (ssname pos_ss cnt)))
      (setq st_pt (trans (get_dt_vl 10 line_dt) 0 1))
      (setq end_pt (trans (get_dt_vl 11 line_dt) 0 1))
      (setq rtx_max (max (car st_pt) (car end_pt)))
      (setq ldx_min (min (car st_pt) (car end_pt)))
      (setq rty_max (max (cadr st_pt) (cadr end_pt)))
      (setq ldy_min (min (cadr st_pt) (cadr end_pt)))
      (setq cnt (1+ cnt))
      (while (< cnt (- ss_ttl 1))
	(setq line_dt (entget (ssname pos_ss cnt)))
	(setq st_pt (trans (get_dt_vl 10 line_dt) 0 1))
	(setq end_pt (trans (get_dt_vl 11 line_dt) 0 1))
	(setq rtx_max (max (car st_pt) (car end_pt) rtx_max))
	(setq ldx_min (min (car st_pt) (car end_pt) ldx_min))
	(setq rty_max (max (cadr st_pt) (cadr end_pt) rty_max))
	(setq ldy_min (min (cadr st_pt) (cadr end_pt) ldy_min))
	(setq cnt (1+ cnt))
      )
    )
    (progn
      (prompt "\没有发现0层的边框！请检查")
      (exit)
    )
  )
  (setq eml_wth (- rtx_max ldx_min))
  (setq eml_high (- rty_max ldy_min))
  (setq
    cnt_pt (list (/ (+ rtx_max ldx_min) 2) (/ (+ rty_max ldy_min) 2))
  )
  (command "move" "all" "" cnt_pt "0,0")
  (command "ZOOM" "e")
  (setq prn_jd (strcase (getstring "\是否打印图形<Y>")))
  (if (= prn_jd "")
    (command "plot" "e" "5" "N" "" "" "" "90" "" "" "" "0")
  )
  (command "layer" "LO" "*" "U" "0" "")
  (command "erase" "all" "")
  (command "layer" "U" "*" "F" "010" "")
  (if (= prn_jd "")
    (progn
      (command "ZOOM" "e")
      (setq ext_max (getvar "extmax"))
      (setq ext_min (getvar "extmin"))
      (if (> (- (car ext_max) (car ext_min))
	     (- (cadr ext_max) (cadr ext_min))
	  )
	(setq prn_agl "90")
	(setq prn_agl "0")
      )
      (command "plot" "e" "5" "N" "" "" "" prn_agl "" "" "" "0")
    )
  )
  (command "layer" "T" "010" "")
  (command "ZOOM" "e")
  (if (< eml_high 385)
      (setq mm_ss (ssget "W" '(-170 -202) '(0 -183)))
      (setq mm_ss (ssget "W" '(-170 -202) '(0 -183)))
    )
      (if mm_ss
	(if (= (sslength mm_ss) 1)
	  (entdel (ssname mm_ss 0))
	)
	(progn
	  (prompt "\请确原客户标识‘日期膜面’是否正确!")
	  (getstring)
	)
      )
  (command "zoom" "0.5x")
  (command "layer" "M" "010" "")
   (if (< eml_high 385)
       (gd)
       (gd16)
    )
  
 
  (setq eml_wth (/ eml_wth 2))
  (setq eml_high (/ eml_high 2))
  (command "pline"
	   (list (- eml_wth 0.05) (- 0.05 eml_high))
	   "w"
	   0
	   0
	   (list (- eml_wth 0.05) (- eml_high 0.05))
	   (list (- 0.05 eml_wth) (- eml_high 0.05))
	   (list (- 0.05 eml_wth) (- 0.05 eml_high))
	   (list (- eml_wth 5) (- 0.05 eml_high))
	   (list (- eml_wth 5) (- (- eml_high) 0.05))
	   (list (- (- eml_wth) 0.05) (- (- eml_high) 0.05))
	   (list (- (- eml_wth) 0.05) (+ eml_high 0.05))
	   (list (+ eml_wth 0.05) (+ eml_high 0.05))
	   (list (+ eml_wth 0.05) (- (- eml_high) 0.05))
	   (list (- eml_wth 4) (- (- eml_high) 0.05))
	   (list (- eml_wth 4) (- 0.05 eml_high))
	   "c"
  )
  (setq chrm (getstring "\现在要加边框，是否加钉？<N>"))
  (if (= (strcase chrm) "Y")
    (progn
      (command "pline"
	       (list (- (- eml_wth) 0.15) (- (- eml_high) 0.15))
	       (list (- (- eml_wth) 0.05) (- (- eml_high) 0.15))
	       (list (- (- eml_wth) 0.05) (- (- eml_high) 0.05))
	       (list (- (- eml_wth) 0.15) (- (- eml_high) 0.05))
	       "c"
      )
      (command "pline"
	       (list (+ eml_wth 0.15) (+ eml_high 0.15))
	       (list (+ eml_wth 0.05) (+ eml_high 0.15))
	       (list (+ eml_wth 0.05) (+ eml_high 0.05))
	       (list (+ eml_wth 0.15) (+ eml_high 0.05))
	       "c"
      )
      (command "pline"
	       (list (- (- eml_wth) 0.15) (+ eml_high 0.15))
	       (list (- (- eml_wth) 0.15) (+ eml_high 0.05))
	       (list (- (- eml_wth) 0.05) (+ eml_high 0.05))
	       (list (- (- eml_wth) 0.05) (+ eml_high 0.15))
	       "c"
      )
      (command "pline"
	       (list (+ eml_wth 0.05) (- (- eml_high) 0.15))
	       (list (+ eml_wth 0.15) (- (- eml_high) 0.15))
	       (list (+ eml_wth 0.15) (- (- eml_high) 0.05))
	       (list (+ eml_wth 0.05) (- (- eml_high) 0.05))
	       "c"
      )
    )
  )

  (command "layer" "C" "GREEN" "000" "")
  (command "layer" "C" "BLUE" "001" "")
)
(prompt "\输入GDSINIT运行")
