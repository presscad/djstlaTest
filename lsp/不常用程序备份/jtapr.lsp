;last modify date 2003-4-5
;add the promotion about the ke,ce,cf
(defun c:jtapr ();锦泰.
  (defun set_var ()
    (setq osnap_old (getvar "osmode"))
    (setq orthomode_old (getvar "orthomode"))
    (setvar "osmode" 0)
    (setvar "orthomode" 0)
    (list osnap_old orthomode_old)
  )
  (defun get_dt_vl (item dt)
    (cdr (assoc item dt))
  )
  (defun draw_edge () 
        (command "pline" (list 190.25 183.25) "w" 0 0 
                         (list 200.0 183.25) 
                         (list 200.0 182.75) 
                         (list 190.25 182.75) 
                         (list 190.25 173.0) 
                         (list 189.75 173.0) 
                         (list 189.75 182.75) 
                         (list 180.0 182.75) 
                         (list 180.0 183.25) 
                         (list 189.75 183.25) 
                         (list 189.75 193.0) 
                         (list 190.25 193.0) 
                         "c"
         )
        (command "pline" (list 172.137 110.665) "w" 0 0 
                         (list 167.5 123.903) 
                         (list 162.863 110.665) 
                         (list 166.0 110.665) 
                         (list 166.0 75.5285) 
                         (list 169.0 75.5285) 
                         (list 169.0 110.665) 
                         "c"
         )
        (command "pline" (list 190.25 -220.25) "w" 0 0 
                         (list 200.0 -220.25) 
                         (list 200.0 -219.75) 
                         (list 190.25 -219.75) 
                         (list 190.25 -210.0) 
                         (list 189.75 -210.0) 
                         (list 189.75 -219.75) 
                         (list 180.0 -219.75) 
                         (list 180.0 -220.25) 
                         (list 189.75 -220.25) 
                         (list 189.75 -230.0) 
                         (list 190.25 -230.0) 
                         "c"
         )
        (command "pline" (list -190.25 183.25) "w" 0 0 
                         (list -200.0 183.25) 
                         (list -200.0 182.75) 
                         (list -190.25 182.75) 
                         (list -190.25 173.0) 
                         (list -189.75 173.0) 
                         (list -189.75 182.75) 
                         (list -180.0 182.75) 
                         (list -180.0 183.25) 
                         (list -189.75 183.25) 
                         (list -189.75 193.0) 
                         (list -190.25 193.0) 
                         "c"
         )
        (command "pline" (list -190.25 -220.25) "w" 0 0 
                         (list -200.0 -220.25) 
                         (list -200.0 -219.75) 
                         (list -190.25 -219.75) 
                         (list -190.25 -210.0) 
                         (list -189.75 -210.0) 
                         (list -189.75 -219.75) 
                         (list -180.0 -219.75) 
                         (list -180.0 -220.25) 
                         (list -189.75 -220.25) 
                         (list -189.75 -230.0) 
                         (list -190.25 -230.0) 
                         "c"
         )
        (command "pline" (list -202.5 228.125) "w" 0 0 
                         (list -202.5 227.875) 
                         (list 202.5 227.875) 
                         (list 202.5 228.125) 
                         "c"
         )
        (command "pline" (list -202.5 229.692) "w" 0 0 
                         (list -202.5 229.442) 
                         (list 202.5 229.442) 
                         (list 202.5 229.692) 
                         "c"
         )
        (command "pline" (list -202.5 232.192) "w" 0 0 
                         (list -202.5 231.942) 
                         (list 202.5 231.942) 
                         (list 202.5 232.192) 
                         "c"
         )
        (command "pline" (list -202.5 234.692) "w" 0 0 
                         (list -202.5 234.442) 
                         (list 202.5 234.442) 
                         (list 202.5 234.692) 
                         "c"
         )
        (command "pline" (list -202.5 237.192) "w" 0 0 
                         (list -202.5 236.942) 
                         (list 202.5 236.942) 
                         (list 202.5 237.192) 
                         "c"
         )
        (command "pline" (list -202.5 239.692) "w" 0 0 
                         (list -202.5 239.442) 
                         (list 202.5 239.442) 
                         (list 202.5 239.692) 
                         "c"
         )
        (command "pline" (list -202.5 242.192) "w" 0 0 
                         (list -202.5 241.942) 
                         (list 202.5 241.942) 
                         (list 202.5 242.192) 
                         "c"
         )
        (command "pline" (list 202.5 245.0) "w" 0 0 
                         (list 204.5 245.0) 
                         (list 204.5 245.0) 
                         (list 204.5 -284.0) 
                         (list 204.5 -284.0) 
                         (list -204.5 -284.0) 
                         (list -204.5 245.0) 
                         (list 202.5 245.0) 
                         (list 202.5 243.0) 
                         (list 202.5 243.0) 
                         (list 202.5 243.0) 
                         (list 202.5 -282.0) 
                         (list 202.5 -282.0) 
                         (list -202.5 -282.0) 
                         (list -202.5 243.0) 
                         (list 202.5 243.0) 
                         "c"
         )
  )
  (defun to_0 ()
    (command "zoom" "E")
    (prompt "/n请选择300X350的框!")
    (setq f16x14 (ssget ":s"))    
    (if	(= (sslength F16X14) 1)
      (progn
	(setq pl_dt (entget (ssname f16x14 0)))
	(while (/= (caar pl_dt) 10)
	  (setq pl_dt (cdr pl_dt))
	)
	(setq mid_x (car (get_dt_vl 10 pl_dt)))
	(setq mid_y (cadr (get_dt_vl 10 pl_dt)))
	(setq pt1 (get_dt_vl 10 pl_dt))
	(setq pl_dt (cdr pl_dt))
	(while (/= (caar pl_dt) 10)
	  (setq pl_dt (cdr pl_dt))
	)
	(setq mid_x (+ mid_x (car (get_dt_vl 10 pl_dt))))
	(setq mid_y (+ mid_y (cadr (get_dt_vl 10 pl_dt))))
	(setq pt2 (get_dt_vl 10 pl_dt))
	(setq pl_dt (cdr pl_dt))
	(while (/= (caar pl_dt) 10)
	  (setq pl_dt (cdr pl_dt))
	)
	(setq mid_x (+ mid_x (car (get_dt_vl 10 pl_dt))))
	(setq mid_y (+ mid_y (cadr (get_dt_vl 10 pl_dt))))
	(setq pt3 (get_dt_vl 10 pl_dt))
	(setq pl_dt (cdr pl_dt))
	(while (/= (caar pl_dt) 10)
	  (setq pl_dt (cdr pl_dt))
	)
	(setq mid_x (+ mid_x (car (get_dt_vl 10 pl_dt))))
	(setq mid_y (+ mid_y (cadr (get_dt_vl 10 pl_dt))))
	(setq pt4 (get_dt_vl 10 pl_dt))
	(setq mid_x (/ mid_x 4))
	(setq mid_y (/ mid_y 4))
	(command "move" "all" "" (list mid_x mid_y) "0,0")
	(command "layer" "M" "scl" "")
	(command "zoom" "E")
	(setq scl_set (ssget "w" '(-149.5 -174.5) '(149.5 174.5) ))
	(if scl_set
	  (command "change" scl_set "" "p" "la" "scl" "")
	)
	(setq ers_set (ssget "c" '(-150.1 -175.1) '(-149.9 -174.9)))
	(if ers_set
	  (command "change" ers_set "" "p" "la" "1" "")
	  )
	(setq ers_set (ssget "c" '(149.9 274.9) '(150.1 175.1)))
	(if ers_set
	  (command "change" ers_set "" "p" "la" "1" "")
	  )
	(arxload "//Supermask/engapp/supermask.cam/lcdcad.arx" (prompt "program has been loaded")) 
	(command "topl" "o" "scl" "")
	(setq res (+ (distance pt1 pt2) (distance pt2 pt3) (distance pt3 pt4) (distance pt4 pt1)))
     )
      (progn
	(prompt "\ncan't find the polyline in 0 layer ")
	(exit)
      )
    )

  )

  (defun chg_txt ()
    (setq pt_lst (list
		   (list -13 -277)
		   (list 206 -277)
		   (list 206 -223)
		   (list -13 -233)
		 )
    )
    (setq
      ss_txt (ssget "WP" pt_lst (list (cons 0 "TEXT")))
    )
    (if	(= (sslength ss_txt) 1)
      (progn
	(setq txt_dt (entget (ssname ss_txt 0)))
	(setq alg_left (list -108 -259 0))
	(setq txt_dt (subst (cons 10 alg_left) (assoc 10 txt_dt) txt_dt))
	(setq apr_id (cdr (assoc 1 txt_dt)))
	(setq c_date (getvar "CDATE"))
	(setq apr_id (strcat apr_id " QINGYI " (itoa (fix c_date))))
	(setq txt_dt (subst (cons 1 apr_id) (assoc 1 txt_dt) txt_dt))
	(setq txt_dt (subst (cons 8 "ofst")(assoc 8 txt_dt) txt_dt))
	(setq txt_dt (subst (cons 40 10)(assoc 40 txt_dt) txt_dt))
	(entmod txt_dt)
      )
      (PROMPT "/n请手工处理文字")
    )
  )

  (defun scale (layer_name ke)
    (command "zoom" "E")
    (setq
      ss_lwpl (ssget "x"
		     (list (cons 0 "lwpolyline") (cons 8 layer_name))
	      )
    )
    (setq ss_all (ssget "x"
		     (list (cons 8 layer_name))
	      )
	  )
    (if (/= (sslength ss_lwpl) (sslength ss_all))
      (progn
	(getstring "\n请对有用图形选做TOPL，然后再执！")
	(exit)
	)
      )	
    (if	ss_lwpl
      (progn
	(setq ss_cnt (sslength ss_lwpl))
	(setq i_loop 0)
	(while (< i_loop ss_cnt)
	  (setq pl_dt (entget (ssname ss_lwpl i_loop)))
	  (setq dt nil)
	  (while pl_dt
	    (if	(/= (caar pl_dt) 10)
	      (setq dt (append dt (list (car pl_dt))))
	      (progn
		(setq scl_x (cadar pl_dt))
		(setq scl_y (* (caddar pl_dt) ke))
		(setq
		  dt (append dt (list (cons 10 (list scl_x scl_y 0))))
		)
	      )
	    )
	    (setq pl_dt (cdr pl_dt))
	  )
	  (entmod dt)
	  (setq i_loop (1+ i_loop))
      )
    ))
    (command "zoom" "E")
    (setq
      ss_lwpl (ssget "x" (list (cons 0 "circle") (cons 8 layer_name)))
    )
    (if	ss_lwpl
      (progn
	(setq ss_cnt (sslength ss_lwpl))
	(setq i_loop 0)
	(while (< i_loop ss_cnt)
	  (setq pl_dt (entget (ssname ss_lwpl i_loop)))
	  (setq cx (* (cadr (assoc 10 pl_dt)) ke))
	  (if (or (< cx -192) (> cx 192))
	    (if	(> cx 0)
	      (setq cx (- cx 0.048))
	      (setq cx (+ cx 0.048))
	    )
	    (progn
	      (setq cr (cdr (assoc 40 pl_dt)))
	      (setq
		pl_dt
		 (subst (cons 40 (+ cr 0.115)) (cons 40 cr) pl_dt)
	      )
	    )
	  )
	  (setq yx (caddr (assoc 10 pl_dt)))
	  (setq
	    dt (subst (cons 10 (list cx yx 0)) (assoc 10 pl_dt) pl_dt)
	  )
	  (setq dt (subst (cons 8 "OK") (assoc 8 pl_dt) dt))
	  (entmake dt)
	  (setq i_loop (1+ i_loop))
	)
      )
    )
  )
  (defun ofst (layer_name cf1 ce1)
    (command "zoom" "E")
    (setq
      ss_lwpl (ssget "x"
		     (list (cons 0 "lwpolyline") (cons 8 layer_name))
	      )
    )
    (if	ss_lwpl
      (progn
	(setq ss_cnt (sslength ss_lwpl))
	(setq i_loop 0)
	(while (< i_loop ss_cnt)
	  (setq pl_dt (entget (ssname ss_lwpl i_loop)))
	  (setq cx 0)
	  (setq cy 0)
	  (setq cnt 0)
	  (setq dt pl_dt)
	  (while pl_dt
	    (if	(= (caar pl_dt) 10)
	      (progn
		(setq cx (+ (cadar pl_dt) cx))
		(setq cy (+ (caddar pl_dt) cy))
		(setq cnt (1+ cnt))
	      )
	    )
	    (setq pl_dt (cdr pl_dt))
	  )
	  (setq cx (/ cx cnt))
	  (setq cy (/ cy cnt))
	  (setq pl_dt dt)
	  (setq dt nil)
	  (while pl_dt
	    (if	(/= (caar pl_dt) 10)
	      (setq dt (append dt (list (car pl_dt))))
	      (progn
		(setq ofst_x (cadar pl_dt))
		(setq ofst_y (caddar pl_dt))
		(if (> ofst_x cx)
		  (setq ofst_x (- ofst_x cf1))
		  (setq ofst_x (+ ofst_x cf1))
		)
		(if (> ofst_y cy)
		  (setq ofst_y (- ofst_y ce1))
		  (setq ofst_y (+ ofst_y ce1))
		)
		(setq dt
		       (append dt (list (cons 10 (list ofst_x ofst_y 0))))
		)
	      )
	    )
	    (setq pl_dt (cdr pl_dt))
	  )
	  (entmod dt)
	  (setq i_loop (1+ i_loop))
	)
      )
    )
  )
  (set_var)
  (initget 1 "Yes No")
  (setq kx (getkword "需要特别系数吗？ (Yes or No) "))
  (if (= kx "Yes")
  (setq	ke 0.9865
	ce 0.4000
	cf 0.3000
  )
  (setq	ke 0.9875
	ce 0.4500
	cf 0.3000
  )
    )
  (getstring (strcat "请确认系数是：Ke=" (rtos ke) "; Ce=" (rtos ce) "; Cf=" (rtos  cf)))
  (command "zoom" "E")
  (vl-load-com)					;explode all inserts
  (setq exp_ss (ssget "x" (list (cons 0 "insert"))))
  (while exp_ss
    (setq sum_cnt (sslength exp_ss))
    (setq cnt 0)
    (while (< cnt sum_cnt)
      (setq ent_name (ssname exp_ss cnt))      
      (setq blk_obj (vlax-ename->vla-object ent_name))
      (vlax-invoke blk_obj 'explode)
      (vlax-invoke blk_obj 'delete)
      (vlax-release-object blk_obj)
      (setq cnt (1+ cnt))
    )
    (setq exp_ss (ssget "x" (list (cons 0 "insert"))))
  )
  (setq dim_set (ssget "x" (list (cons 0 "dim*"))))
  (command "erase" dim_set "")  
  (setq fram_len (to_0))
  (scale "scl" ke)
  (if (< fram_len 1299.00)
    (progn
      (getstring "\n请注意此张版的ITO尺寸不是300X350, 程序已经按300X320做了移动,请确认!")
      (setq ss_mv (ssget "x" (list (cons 8 "scl"))))
      (command "move" ss_mv "" "0,0" "0,15")
      )
    )
  (command "layer" "M" "ofst" "")
  (prompt "\n请选中所有单粒！")
  (setq cells (ssget))
  (command "change" cells "" "p" "la" "ofst" "")
  (ofst "ofst" (/ cf 2) (/ ce 2))
  (setq e_set (ssget "x" (list (cons 8 "scl"))))
  (command "change" e_set "" "p" "la" "ofst" "")
  (chg_txt)
  (command "layer" "m" "old" "lock" "ofst" "")
  (command "change" "all" "" "p" "la" "old" "")
  (command "layer" "m" "0" "lock" "old" "unlock" "ofst" "")
  (command "chnage" "all" "" "p" "la" "0" "")  
  (command "layer" "color" "red" "" "off" "old" "")  
  (draw_edge)
  (command "change" "all" "" "p" "la" "0" "")
  (command "purge"   "all"  ""	"N")
  (command "purge"   "all" ""  "n")
  (command "purge"   "all"  ""	"N")
  (command "purge"   "all" ""  "n")
  (command "zoom" "E")
  (if (= kx "Yes")
    (getstring "请手工将中间1/2的单粒上移0.2mm!")
    )
)
(PROMPT "\n 输入 JTAPR 运行程序。")
