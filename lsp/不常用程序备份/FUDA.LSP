(defun set_var ()
  (setq osnap_old (getvar "osmode"))
  (setq orthomode_old (getvar "orthomode"))
  (setvar "osmode" 0)
  (setvar "orthomode" 0)
  (list osnap_old orthomode_old)
)
(defun apr_scale (ss_lwpl x_scl y_scl)
      (setq ss_cnt (sslength ss_lwpl))
      (setq i_loop 0)
      (while (< i_loop ss_cnt)
	(setq pl_dt (entget (ssname ss_lwpl i_loop)))
	(setq dt nil)
	(while pl_dt
	  (if (/= (caar pl_dt) 10)
	    (setq dt (append dt (list (car pl_dt))))
	    (progn
	      (setq scl_x (* (cadar pl_dt) x_scl))
	      (setq scl_y (* (caddar pl_dt) y_scl))
	      (setq
		dt (append dt (list (cons 10 (list scl_x scl_y 0))))
	      )
	    )
	  )
	  (setq pl_dt (cdr pl_dt))
	)
	(entmod dt)
	(setq i_loop (1+ i_loop))
      )
)
(defun apr_ofst (ss_lwpl x_cpt y_cpt)
  (setq x_cpt (/ x_cpt 2.0))
  (setq y_cpt (/ y_cpt 2.0))
  (if ss_lwpl
    (progn
      (setq ss_cnt (sslength ss_lwpl))
      (setq i_loop 0)
      (while (< i_loop ss_cnt)
	(setq pl_dt (entget (ssname ss_lwpl i_loop)))
	(setq cx 0)
	(setq cy 0)
	(setq cnt 0)
	(setq dt pl_dt)
	(while pl_dt
	  (if (= (caar pl_dt) 10)
	    (progn
	      (setq cx (+ (cadar pl_dt) cx))
	      (setq cy (+ (caddar pl_dt) cy))
	      (setq cnt (1+ cnt))
	    )
	  )
	  (setq pl_dt (cdr pl_dt))
	)
	(setq cx (/ cx cnt))
	(setq cy (/ cy cnt))
	(setq pl_dt dt)
	(setq dt nil)
	(while pl_dt
	  (if (/= (caar pl_dt) 10)
	    (setq dt (append dt (list (car pl_dt))))
	    (progn
	      (setq ofst_x (cadar pl_dt))
	      (setq ofst_y (caddar pl_dt))
	      (if (> ofst_x cx)
		(setq ofst_x (- ofst_x x_cpt))
		(setq ofst_x (+ ofst_x x_cpt))
	      )
	      (if (> ofst_y cy)
		(setq ofst_y (- ofst_y y_cpt))
		(setq ofst_y (+ ofst_y y_cpt))
	      )
	      (setq dt
		     (append dt (list (cons 10 (list ofst_x ofst_y 0))))
	      )
	    )
	  )
	  (setq pl_dt (cdr pl_dt))
	)
	(entmod dt)
	(setq i_loop (1+ i_loop))
      )
    )
  )
)
					;(set_var)
					;(setq	ke 0.97880
					;ce 0.2000
					;)
					;(command "zoom" "E")
					;(scale "a" ke)
					;(ofst "a" (/ ce 2))
					;(scale "b" ke) 
					;)
(defun c:fuda ()
  (defun join_line ()
    (setq l_ss (ssget "x" (list (cons 0 "line"))))
    (while l_ss
      (setq l_name (ssname l_ss 0))
      (command "pedit" l_name "Y" "j" "all" "" "")
      (setq l_ss (ssget "x" (list (cons 0 "line"))))
    )
  )
  (defun join_lwpline ()
    (command "convert" "P" "a")
    (setq l_ss
	   (ssget "x"
		  (list (cons 0 "lwpolyline") (cons -4 "!=") (cons 70 1))
	   )
    )
    (setq cnt 0)
    (while (and l_ss (< cnt 100))
      (setq l_name (ssname l_ss 0))
      (command "pedit" l_name "j" "all" "" "")
      (setq
	l_ss (ssget
	       "x"
	       (list (cons 0 "lwpolyline") (cons -4 "!=") (cons 70 1))
	     )
      )
      (setq cnt (1+ cnt))
    )
  )

   (defun vid_chk ()
    (setq
      pl_ss
       (ssget "x"
	      (list (cons 0 "lwpolyline") (cons 41 0.0) (cons 70 1))
       )
    )
    (if	pl_ss
      (setq lwpl_nu (sslength pl_ss))
      (setq lwpl_nu 0)
    )
    (setq
      pl_ss
       (ssget "x"
	      (list (cons 0 "polyline") (cons 41 0.0) (cons 70 1))
       )
    )
    (if	pl_ss
      (setq pl_nu (sslength pl_ss))
      (setq pl_nu 0)
    )
    (setq
      pl_ss
       (ssget "x"
	      (list (cons 0 "circle"))
       )
    )
    (if	pl_ss
      (setq circle_nu (sslength pl_ss))
      (setq circle_nu 0)
    )
    (setq
      pl_ss
       (ssget "x")
    )
    (setq all_nu (sslength pl_ss))
    (setq not_invid (- all_nu (+ (+ lwpl_nu pl_nu) circle_nu)))
    (if	(> not_invid 1)
      (progn
	(prompt	(strcat	(strcat "\n 有" (itoa (- not_invid 1)))
			"个不合法实体.任意键退出"
		)
	)
	(getstring)
	(exit)
      )
    )
    (prompt "\n")
  )
  (defun fix_text ()
    (setq
      ss_txt (ssget "x" (list (cons 0 "TEXT")))
    )
    (if	(= (sslength ss_txt) 1)
      (progn
	(setq txt_dt (entget (ssname ss_txt 0)))
	(setq apr_id (cdr (assoc 1 txt_dt)))
	(setq c_date (getvar "CDATE"))
	(setq apr_id (strcat apr_id " QINGYI " (itoa (fix c_date))))
	(setq txt_dt (subst (cons 1 apr_id) (assoc 1 txt_dt) txt_dt))
	(entmod txt_dt)
      )
      (progn
	(prompt "/n文字有错误的，任意键退出")
	(getstring)
	(exit)
      )
    )
  )
  (defun ofst_pnt (p x_ofst y_ofst)
    (setq x_val (car p))
    (setq y_val (cadr p))
    (list
      (+ x_val x_ofst)
      (+ y_val y_ofst)
    )
  )
  (set_var)					;程序开始
  (setvar "plinewid" 0.0)
  (command "layer" "On" "*" "T" "*" "U" "*" "")
  (command "zoom" "all")
  (setvar "OSMODE" 32)
  (setq dim_ss (ssget "x" (list (cons 0 "dimension"))))
  (if dim_ss
    (command "erase" dim_ss "")
  )
  (setq Ld_pnt (getpoint "\n请选左下角外框线交点"))
  (setq Ru_pnt (getpoint "\n请选右上角外框线交点"))
  (setvar "OSMODE" 0)
  (command "zoom" "w" ld_pnt Ru_pnt)
  (command "zoom" "0.9x")
  (command "erase" "all" "R" "W" Ld_pnt Ru_pnt "")
  (command "zoom" "0.9X")
  (setq xl (car Ld_pnt))
  (setq xr (car Ru_pnt))
  (setq yd (cadr Ld_pnt))
  (setq yu (cadr Ru_pnt))
  (setq apr_size (strcat (rtos (- xr xl)) (strcat "X" (rtos (- yu yd))))) 
  (command "layer" "M" "APR" "")
  (command "PURGE" "A" "" "N")
  (command "PURGE" "A" "" "N")
  (command "PURGE" "A" "" "N")
  (command "PURGE" "A" "" "N")
  (command "pline"
	   ld_pnt
	   (list xr yd)
	   (list xr yu)
	   (list (+ xr 2) (+ yu 2))
	   (list (+ xr 2) (- yd 2))
	   (list (- xl 2) (- yd 2))
	   (list (- xl 2) (+ yu 2))
	   (list (+ 2 xr) (+ yu 2))
	   (list xr yu)
	   (list xl yu)
	   "c"
	   ""
  )
  (getstring "\n请确认边框是否对齐（总体）")
  (command "zoom"
	   "W"
	   (ofst_pnt Ld_pnt -5 -5)
	   (ofst_pnt Ld_pnt 5 5)
  )
  (getstring "\n请确认边框左下角是否对齐")
  (command "zoom"
	   "W"
	   (ofst_pnt Ru_pnt -5 -5)
	   (ofst_pnt Ru_pnt 5 5)
  )
  (getstring "\n请确认边框右上角是否对齐")
  (command "layer" "lock" "apr" "")
  (command "erase" "all" "")
  (command "layer" "unlock" "apr" "")
  (command "PURGE" "A" "" "N")
  (setvar "osmode" 2)
  (command "zoom" "w" Ld_pnt (ofst_pnt ld_pnt 150 150))
  (setq cell_ld_pnt (getpoint "\n请选择左下角的单粒下边的中心"))
  (command "zoom" "w" Ru_pnt (ofst_pnt Ru_pnt -150 -150))
  (setq cell_ru_pnt (getpoint "\n请选择右上角的单粒上边的中心"))
  (setq	mid_pnt	(list (/ (+ (car cell_ld_pnt) (car cell_ru_pnt)) 2)
		      (/ (+ (cadr cell_ld_pnt) (cadr cell_ru_pnt)) 2)
		)
  )
  (command "move" "all" "" mid_pnt '(0 0))
  (setq	cell_ld_pnt
	 (ofst_pnt cell_ld_pnt
		   (- (car mid_pnt))
		   (- (cadr mid_pnt))
	 )
  )
  (setq	cell_ru_pnt
	 (ofst_pnt cell_ru_pnt
		   (- (car mid_pnt))
		   (- (cadr mid_pnt))
	 )
  )
  (setvar "osmode" 0)
  (command "zoom" "all")
  (join_line)
  (join_lwpline)
  (fix_text)
  (command "zoom" "w" (ofst_pnt cell_ld_pnt -50 -50) (ofst_pnt cell_ld_pnt 50 50))
  (setq fst_pnt (getpoint "请用窗选选择两条DUMMY线"))
  (setq scd_pnt (getcorner fst_pnt))
  (setq	cell_ss	(ssget "C"
		       fst_pnt
		       scd_pnt
		)
  )
  (if cell_ss
    (if	(= (sslength cell_ss) 2)
      (progn
	(setq pl_dt (entget (ssname cell_ss 0)))
	(setq fst_pnt (assoc 10 pl_dt))
	(setq pl_dt (member fst_pnt pl_dt))
	(setq pl_dt (cdr pl_dt))
	(setq fst_pnt (cdr fst_pnt))
	(setq max_x (car fst_pnt))
	(setq max_y (cadr fst_pnt))
	(setq min_x max_x)
	(setq min_y max_y)
	(while pl_dt
	  (setq fst_pnt (assoc 10 pl_dt))
	  (setq pl_dt (member fst_pnt pl_dt))
	  (setq pl_dt (cdr pl_dt))
	  (if fst_pnt
	    (progn
	      (setq fst_pnt (cdr fst_pnt))
	      (if (< max_x (car fst_pnt))
		(setq max_x (car fst_pnt))
	      )
	      (if (< max_y (cadr fst_pnt))
		(setq max_y (cadr fst_pnt))
	      )
	      (if (> min_x (car fst_pnt))
		(setq min_x (car fst_pnt))
	      )
	      (if (> min_y (cadr fst_pnt))
		(setq min_y (cadr fst_pnt))
	      )
	    )
	  )	  
	)
	(command "zoom" "e")
	(if (> (- max_x min_x) (- max_y min_y))
	  (progn
	    (setq prt_drict "Y")
	    (setq cell1_ss (ssget "C" cell_ld_pnt cell_ru_pnt))
	    (if	cell_ss
	      (progn
		(apr_ofst cell1_ss 0.0 0.2)
		(apr_scale cell1_ss 1.0 0.9788)
	      )
	      (progn
		(prompt "程序无法找到单粒的位置，任意键退出！")
		(getstring)
		(exit)
	      )
	    )
	    (apr_scale cell_ss 1.0 0.9788)
	  )
	  (progn
	    (setq prt_drict "Y")
	    (setq cell1_ss (ssget "C" cell_ld_pnt cell_ru_pnt))
	    (if	cell_ss
	      (progn
		(apr_ofst cell1_ss 0.2 0.0)
		(apr_scale cell1_ss 0.9788 1)
	      )
	      (progn
		(prompt "程序无法找到单粒的位置，任意键退出！")
		(getstring)
		(exit)
	      )
	    )
	    (apr_scale cell_ss 0.9788 1)	    
	  )
	)
      )
      (progn
	(prompt "/n找不两条DUMMY线，任意键退出")
	(getstring)
	(exit)
      )
    )
  )
  (command "change" "all" "" "P" "LA" "0" "")
  (command "layer" "m" "0" "")
  (command "PURGE" "A" "" "N")
  (prompt "\n结果报告:")
  (prompt (strcat "\n印刷方向为：" prt_drict))
  (prompt (strcat "\n版的尺寸(xXy:" apr_size))
  (prompt "\nOK,请按F2键看结果报告,确认程序处理是否正确")
)
(prompt "\n请输入FUDA运行")
