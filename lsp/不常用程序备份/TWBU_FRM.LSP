(defun c:twbu () 
        (command "pline" (list 80.6029 -155.815) "w" 0 0 
                         (list 81.8302 -155.809) 
                         (list 81.8364 -155.926) 
                         (list 81.5034 -155.951) 
                         (list 81.3245 -155.97) 
                         (list 80.4734 -156.549) 
                         (list 81.7439 -157.77) 
                         (list 81.8549 -157.794) 
                         (list 82.1879 -157.794) 
                         (list 82.2064 -157.911) 
                         (list 80.4488 -157.93) 
                         (list 80.4364 -157.788) 
                         (list 80.7448 -157.782) 
                         (list 79.8135 -156.9) 
                         (list 79.8074 -156.925) 
                         (list 79.7889 -156.95) 
                         (list 79.8074 -157.77) 
                         (list 79.8444 -157.807) 
                         (list 80.1959 -157.807) 
                         (list 80.2082 -157.899) 
                         (list 80.1774 -157.924) 
                         (list 78.5554 -157.936) 
                         (list 78.5431 -157.893) 
                         (list 78.5431 -157.819) 
                         (list 78.5986 -157.807) 
                         (list 78.9316 -157.788) 
                         (list 78.9131 -155.976) 
                         (list 78.6294 -155.97) 
                         (list 78.5431 -155.963) 
                         (list 78.5308 -155.852) 
                         (list 78.6109 -155.834) 
                         (list 80.1836 -155.822) 
                         (list 80.1836 -155.933) 
                         (list 80.1589 -155.963) 
                         (list 79.8135 -155.97) 
                         (list 79.7889 -156.025) 
                         (list 79.7889 -156.771) 
                         (list 79.8197 -156.796) 
                         (list 80.9915 -156.0) 
                         (list 80.9668 -155.945) 
                         (list 80.6646 -155.957) 
                         (list 80.5844 -155.939) 
                         (list 80.5844 -155.84) 
                         "c"
         )
        (command "pline" (list 76.3537 -157.332) "w" 0 0 
                         (list 76.3167 -157.393) 
                         (list 76.3229 -157.93) 
                         (list 76.3846 -157.967) 
                         (list 76.5696 -157.967) 
                         (list 76.6436 -157.917) 
                         (list 76.7546 -157.862) 
                         (list 76.841 -157.905) 
                         (list 77.0321 -157.954) 
                         (list 77.2603 -157.991) 
                         (list 77.5317 -157.998) 
                         (list 77.8092 -157.991) 
                         (list 78.0189 -157.948) 
                         (list 78.2779 -157.831) 
                         (list 78.4753 -157.671) 
                         (list 78.5554 -157.591) 
                         (list 78.6048 -157.455) 
                         (list 78.6356 -157.289) 
                         (list 78.6294 -157.104) 
                         (list 78.5493 -156.95) 
                         (list 78.4999 -156.857) 
                         (list 78.4013 -156.789) 
                         (list 78.2656 -156.715) 
                         (list 78.0867 -156.654) 
                         (list 77.8955 -156.598) 
                         (list 77.7105 -156.555) 
                         (list 77.5564 -156.531) 
                         (list 77.3898 -156.5) 
                         (list 77.2542 -156.469) 
                         (list 77.0815 -156.444) 
                         (list 76.9643 -156.401) 
                         (list 76.841 -156.376) 
                         (list 76.7855 -156.346) 
                         (list 76.7423 -156.29) 
                         (list 76.7423 -156.228) 
                         (list 76.7484 -156.179) 
                         (list 76.7731 -156.117) 
                         (list 76.8471 -156.062) 
                         (list 76.9458 -156.013) 
                         (list 77.026 -155.988) 
                         (list 77.1061 -155.976) 
                         (list 77.1987 -155.945) 
                         (list 77.3467 -155.945) 
                         (list 77.4947 -155.945) 
                         (list 77.6735 -155.97) 
                         (list 77.8215 -156.031) 
                         (list 77.9449 -156.074) 
                         (list 78.0497 -156.21) 
                         (list 78.1299 -156.327) 
                         (list 78.1854 -156.401) 
                         (list 78.2409 -156.426) 
                         (list 78.3704 -156.426) 
                         (list 78.3828 -156.389) 
                         (list 78.3828 -155.859) 
                         (list 78.3334 -155.834) 
                         (list 78.1731 -155.846) 
                         (list 78.1237 -155.902) 
                         (list 78.0682 -155.92) 
                         (list 78.0251 -155.92) 
                         (list 77.9634 -155.92) 
                         (list 77.8832 -155.883) 
                         (list 77.6859 -155.828) 
                         (list 77.4885 -155.809) 
                         (list 77.3158 -155.803) 
                         (list 77.1493 -155.809) 
                         (list 76.9705 -155.84) 
                         (list 76.7978 -155.914) 
                         (list 76.6498 -155.976) 
                         (list 76.5696 -156.056) 
                         (list 76.4648 -156.154) 
                         (list 76.3908 -156.272) 
                         (list 76.3352 -156.444) 
                         (list 76.3537 -156.592) 
                         (list 76.3908 -156.752) 
                         (list 76.4771 -156.845) 
                         (list 76.5634 -156.9) 
                         (list 76.7299 -156.98) 
                         (list 76.9643 -157.061) 
                         (list 77.1617 -157.11) 
                         (list 77.322 -157.128) 
                         (list 77.4577 -157.135) 
                         (list 77.6242 -157.159) 
                         (list 77.7969 -157.19) 
                         (list 77.9819 -157.239) 
                         (list 78.0929 -157.307) 
                         (list 78.1731 -157.393) 
                         (list 78.2162 -157.474) 
                         (list 78.2101 -157.597) 
                         (list 78.1237 -157.72) 
                         (list 78.0189 -157.77) 
                         (list 77.9017 -157.831) 
                         (list 77.7907 -157.856) 
                         (list 77.6735 -157.862) 
                         (list 77.5317 -157.88) 
                         (list 77.3713 -157.874) 
                         (list 77.2357 -157.85) 
                         (list 77.0198 -157.807) 
                         (list 76.8965 -157.726) 
                         (list 76.7793 -157.646) 
                         (list 76.6744 -157.541) 
                         (list 76.5881 -157.424) 
                         (list 76.5511 -157.357) 
                         "c"
         )
        (command "pline" (list 72.4112 -157.967) "w" 0 0 
                         (list 73.4226 -157.961) 
                         (list 74.9891 -156.685) 
                         (list 74.619 -157.763) 
                         (list 74.4834 -157.948) 
                         (list 75.4208 -157.967) 
                         (list 76.093 -155.791) 
                         (list 75.1433 -155.803) 
                         (list 72.5345 -157.887) 
                         (list 72.4112 -157.936) 
                         "c"
         )
        (command "pline" (list 56.3069 -155.939) "w" 0 0 
                         (list 56.4117 -155.92) 
                         (list 57.898 -155.914) 
                         (list 57.9659 -155.957) 
                         (list 57.9597 -156.05) 
                         (list 57.935 -156.062) 
                         (list 57.528 -156.062) 
                         (list 57.528 -157.369) 
                         (list 57.5403 -157.449) 
                         (list 57.5588 -157.585) 
                         (list 57.5958 -157.659) 
                         (list 57.6328 -157.776) 
                         (list 57.7377 -157.862) 
                         (list 57.8857 -157.905) 
                         (list 58.0029 -157.911) 
                         (list 58.2002 -157.924) 
                         (list 58.3544 -157.911) 
                         (list 58.5209 -157.893) 
                         (list 58.6443 -157.862) 
                         (list 58.7799 -157.813) 
                         (list 58.8848 -157.708) 
                         (list 58.9465 -157.578) 
                         (list 58.9588 -157.517) 
                         (list 58.965 -157.35) 
                         (list 58.9588 -157.005) 
                         (list 58.9588 -156.148) 
                         (list 58.9465 -156.093) 
                         (list 58.9094 -156.068) 
                         (list 58.8909 -156.056) 
                         (list 58.6258 -156.068) 
                         (list 58.5579 -156.037) 
                         (list 58.5579 -155.926) 
                         (list 58.6073 -155.92) 
                         (list 59.409 -155.908) 
                         (list 59.4275 -155.963) 
                         (list 59.4275 -156.031) 
                         (list 59.335 -156.062) 
                         (list 59.2425 -156.074) 
                         (list 59.2116 -156.124) 
                         (list 59.1993 -156.173) 
                         (list 59.1931 -156.235) 
                         (list 59.2116 -157.486) 
                         (list 59.1931 -157.603) 
                         (list 59.1561 -157.677) 
                         (list 59.1006 -157.77) 
                         (list 59.039 -157.843) 
                         (list 58.9526 -157.893) 
                         (list 58.7861 -157.961) 
                         (list 58.6443 -158.01) 
                         (list 58.5086 -158.041) 
                         (list 58.4531 -158.053) 
                         (list 57.6637 -158.072) 
                         (list 57.5897 -158.059) 
                         (list 57.4108 -158.035) 
                         (list 57.2505 -158.004) 
                         (list 57.0531 -157.948) 
                         (list 56.9544 -157.893) 
                         (list 56.8804 -157.868) 
                         (list 56.8249 -157.813) 
                         (list 56.7879 -157.745) 
                         (list 56.7448 -157.665) 
                         (list 56.7139 -157.548) 
                         (list 56.6954 -157.375) 
                         (list 56.6954 -157.184) 
                         (list 56.6954 -156.124) 
                         (list 56.6769 -156.068) 
                         (list 56.6461 -156.062) 
                         (list 56.3069 -156.068) 
                         (list 56.2946 -156.019) 
                         "c"
         )
        (command "pline" (list 50.8533 -158.31) "w" 0 0 
                         (list 56.036 -156.059) 
                         (list 56.0672 -156.105) 
                         (list 56.036 -156.137) 
                         (list 54.641 -156.729) 
                         (list 54.6332 -156.791) 
                         (list 52.8718 -157.508) 
                         (list 52.8407 -157.585) 
                         (list 50.939 -158.38) 
                         "c"
         )
        (command "pline" (list 51.1573 -158.575) "w" 0 0 
                         (list 51.0637 -158.497) 
                         (list 51.0482 -158.481) 
                         (list 55.9815 -156.362) 
                         (list 56.0438 -156.362) 
                         (list 56.0672 -156.409) 
                         (list 54.8436 -156.923) 
                         (list 54.6566 -156.986) 
                         (list 54.6566 -157.056) 
                         (list 52.8641 -157.78) 
                         (list 52.8641 -157.843) 
                         "c"
         )
        (command "pline" (list 51.3131 -158.653) "w" 0 0 
                         (list 55.9113 -156.674) 
                         (list 55.9659 -156.666) 
                         (list 55.9971 -156.69) 
                         (list 54.6566 -157.274) 
                         (list 54.6644 -157.321) 
                         (list 52.903 -158.045) 
                         (list 52.9108 -158.115) 
                         (list 51.6093 -158.668) 
                         (list 51.6405 -158.699) 
                         (list 51.469 -158.723) 
                         (list 51.3989 -158.715) 
                         "c"
         )
        (command "pline" (list 51.5703 -158.808) "w" 0 0 
                         (list 55.8802 -156.978) 
                         (list 55.9035 -156.986) 
                         (list 55.9269 -157.009) 
                         (list 55.9113 -157.048) 
                         (list 54.7033 -157.547) 
                         (list 54.6877 -157.578) 
                         (list 52.9108 -158.325) 
                         (list 52.9186 -158.372) 
                         (list 52.3653 -158.629) 
                         (list 52.2406 -158.653) 
                         (list 52.2172 -158.676) 
                         (list 52.2873 -158.692) 
                         (list 52.2562 -158.723) 
                         (list 52.1548 -158.715) 
                         (list 52.1393 -158.715) 
                         (list 51.8665 -158.847) 
                         (list 51.695 -158.886) 
                         (list 51.5859 -158.816) 
                         "c"
         )
        (command "pline" (list 51.921 -158.949) "w" 0 0 
                         (list 55.7399 -157.336) 
                         (list 55.7555 -157.367) 
                         (list 55.771 -157.398) 
                         (list 54.6799 -157.843) 
                         (list 54.6644 -157.874) 
                         (list 53.4875 -158.372) 
                         (list 52.903 -158.614) 
                         (list 52.8952 -158.645) 
                         (list 52.8952 -158.684) 
                         (list 52.9186 -158.715) 
                         (list 52.7627 -158.731) 
                         (list 52.1704 -159.011) 
                         (list 52.0613 -159.034) 
                         (list 52.0146 -159.019) 
                         "c"
         )
        (command "pline" (list 52.2795 -159.073) "w" 0 0 
                         (list 55.4203 -157.733) 
                         (list 55.4437 -157.71) 
                         (list 55.5216 -157.695) 
                         (list 55.5139 -157.741) 
                         (list 55.4905 -157.788) 
                         (list 54.7345 -158.1) 
                         (list 54.7111 -158.185) 
                         (list 53.5187 -158.676) 
                         (list 53.4953 -158.684) 
                         (list 53.5577 -158.715) 
                         (list 53.3706 -158.715) 
                         (list 53.0199 -158.855) 
                         (list 52.9576 -158.863) 
                         (list 52.9342 -158.918) 
                         (list 52.9264 -158.972) 
                         (list 52.5991 -159.112) 
                         (list 52.451 -159.112) 
                         "c"
         )
        (command "pline" (list 52.8796 -159.12) "w" 0 0 
                         (list 52.9498 -159.066) 
                         (list 55.1476 -158.131) 
                         (list 55.1709 -158.162) 
                         (list 55.1398 -158.201) 
                         (list 54.8748 -158.31) 
                         (list 54.7345 -158.372) 
                         (list 54.7267 -158.435) 
                         (list 54.1967 -158.645) 
                         (list 54.1422 -158.637) 
                         (list 54.15 -158.676) 
                         (list 54.2123 -158.699) 
                         (list 54.0409 -158.715) 
                         (list 53.0667 -159.128) 
                         "c"
         )
        (command "pline" (list 52.4822 -157.404) "w" 0 0 
                         (list 57.735 -155.184) 
                         (list 57.6493 -155.106) 
                         (list 57.5636 -155.067) 
                         (list 55.623 -155.908) 
                         (list 55.6775 -155.947) 
                         (list 53.9318 -156.695) 
                         (list 53.8382 -156.765) 
                         (list 52.4432 -157.373) 
                         "c"
         )
        (command "pline" (list 52.4588 -157.116) "w" 0 0 
                         (list 52.5601 -157.123) 
                         (list 57.4778 -154.981) 
                         (list 57.3999 -154.927) 
                         (list 57.2752 -154.919) 
                         (list 55.6308 -155.62) 
                         (list 55.6697 -155.682) 
                         (list 53.8694 -156.414) 
                         (list 53.8305 -156.461) 
                         (list 53.7369 -156.516) 
                         (list 52.4666 -157.069) 
                         "c"
         )
        (command "pline" (list 52.5367 -156.812) "w" 0 0 
                         (list 57.2362 -154.81) 
                         (list 57.1661 -154.74) 
                         (list 57.0492 -154.732) 
                         (list 56.9868 -154.747) 
                         (list 55.7165 -155.316) 
                         (list 55.6541 -155.355) 
                         (list 55.623 -155.425) 
                         (list 53.8694 -156.15) 
                         (list 53.846 -156.196) 
                         (list 52.5055 -156.765) 
                         "c"
         )
        (command "pline" (list 52.6069 -156.477) "w" 0 0 
                         (list 52.7082 -156.477) 
                         (list 52.8251 -156.446) 
                         (list 56.9557 -154.631) 
                         (list 56.831 -154.592) 
                         (list 56.7141 -154.592) 
                         (list 55.6074 -155.067) 
                         (list 55.6074 -155.129) 
                         (list 53.8305 -155.869) 
                         (list 53.7993 -155.908) 
                         (list 53.7058 -155.963) 
                         (list 52.5835 -156.453) 
                         "c"
         )
        (command "pline" (list 52.7627 -156.126) "w" 0 0 
                         (list 52.8952 -156.095) 
                         (list 56.6439 -154.498) 
                         (list 56.5192 -154.459) 
                         (list 56.3711 -154.444) 
                         (list 56.3322 -154.451) 
                         (list 55.6308 -154.763) 
                         (list 55.584 -154.872) 
                         (list 53.8227 -155.597) 
                         (list 53.6434 -155.706) 
                         (list 52.7861 -156.072) 
                         (list 52.7471 -156.111) 
                         "c"
         )
        (command "pline" (list 53.0121 -155.737) "w" 0 0 
                         (list 53.0745 -155.745) 
                         (list 56.2231 -154.405) 
                         (list 56.0828 -154.366) 
                         (list 55.9035 -154.374) 
                         (list 55.5684 -154.529) 
                         (list 55.5918 -154.561) 
                         (list 53.8305 -155.293) 
                         (list 53.8227 -155.355) 
                         (list 53.0121 -155.706) 
                         "c"
         )
        (command "pline" (list 53.4174 -155.269) "w" 0 0 
                         (list 53.4486 -155.293) 
                         (list 53.5577 -155.254) 
                         (list 55.7087 -154.35) 
                         (list 55.6074 -154.327) 
                         (list 55.4983 -154.327) 
                         (list 53.7681 -155.051) 
                         (list 53.7603 -155.106) 
                         (list 53.4018 -155.254) 
                         "c"
         )
        (command "pline" (list 70.4056 -157.843) "w" 0 0 
                         (list 70.3563 -157.856) 
                         (list 70.3624 -157.954) 
                         (list 70.4241 -157.967) 
                         (list 71.9906 -157.967) 
                         (list 72.0337 -157.942) 
                         (list 72.0337 -157.843) 
                         (list 71.9536 -157.831) 
                         (list 71.602 -157.831) 
                         (list 71.5835 -156.007) 
                         (list 71.9474 -156.013) 
                         (list 72.0091 -155.976) 
                         (list 72.0152 -155.896) 
                         (list 71.9906 -155.871) 
                         (list 71.9351 -155.859) 
                         (list 70.6646 -155.865) 
                         (list 70.1034 -157.005) 
                         (list 70.0787 -157.024) 
                         (list 69.499 -155.871) 
                         (list 68.1114 -155.877) 
                         (list 68.0991 -155.994) 
                         (list 68.1546 -156.019) 
                         (list 68.5246 -156.019) 
                         (list 68.5308 -157.72) 
                         (list 68.5184 -157.776) 
                         (list 68.4876 -157.837) 
                         (list 68.3951 -157.85) 
                         (list 68.3026 -157.868) 
                         (list 68.3026 -157.942) 
                         (list 68.3149 -157.967) 
                         (list 69.1475 -157.979) 
                         (list 69.1783 -157.954) 
                         (list 69.1783 -157.887) 
                         (list 69.1537 -157.85) 
                         (list 68.8083 -157.843) 
                         (list 68.7713 -157.788) 
                         (list 68.7466 -157.726) 
                         (list 68.7281 -156.111) 
                         (list 68.7466 -156.117) 
                         (list 69.6039 -157.911) 
                         (list 69.6532 -157.967) 
                         (list 69.8444 -157.961) 
                         (list 70.7201 -156.142) 
                         (list 70.751 -156.093) 
                         (list 70.7756 -156.161) 
                         (list 70.7818 -157.813) 
                         (list 70.7756 -157.837) 
                         (list 70.4488 -157.843) 
                         "c"
         )
        (command "pline" (list 59.5878 -155.914) "w" 0 0 
                         (list 59.594 -156.037) 
                         (list 59.7235 -156.044) 
                         (list 59.7914 -156.056) 
                         (list 59.7975 -157.862) 
                         (list 59.779 -157.887) 
                         (list 59.4213 -157.887) 
                         (list 59.409 -157.911) 
                         (list 59.409 -157.991) 
                         (list 59.4398 -158.01) 
                         (list 59.483 -158.022) 
                         (list 61.068 -158.016) 
                         (list 61.105 -157.991) 
                         (list 61.1111 -157.905) 
                         (list 61.0741 -157.868) 
                         (list 60.6486 -157.862) 
                         (list 60.6424 -157.153) 
                         (list 60.6548 -157.085) 
                         (list 60.6733 -157.061) 
                         (list 60.7349 -157.061) 
                         (list 60.8151 -157.054) 
                         (list 60.883 -157.054) 
                         (list 61.1481 -157.048) 
                         (list 61.3578 -157.042) 
                         (list 61.586 -157.048) 
                         (list 61.7217 -157.017) 
                         (list 61.9375 -156.98) 
                         (list 62.1041 -156.919) 
                         (list 62.2706 -156.82) 
                         (list 62.3692 -156.722) 
                         (list 62.4371 -156.611) 
                         (list 62.4433 -156.537) 
                         (list 62.4556 -156.432) 
                         (list 62.4186 -156.321) 
                         (list 62.3754 -156.228) 
                         (list 62.3076 -156.142) 
                         (list 62.1657 -156.068) 
                         (list 62.0424 -156.007) 
                         (list 61.8944 -155.976) 
                         (list 61.734 -155.957) 
                         (list 61.6583 -155.952) 
                         (list 60.6301 -156.05) 
                         (list 60.9015 -156.044) 
                         (list 61.0556 -156.031) 
                         (list 61.2468 -156.044) 
                         (list 61.3887 -156.093) 
                         (list 61.4565 -156.173) 
                         (list 61.4997 -156.272) 
                         (list 61.5182 -156.383) 
                         (list 61.512 -156.518) 
                         (list 61.5243 -156.629) 
                         (list 61.4997 -156.728) 
                         (list 61.4997 -156.752) 
                         (list 61.4318 -156.87) 
                         (list 61.3578 -156.907) 
                         (list 61.3085 -156.919) 
                         (list 61.1605 -156.919) 
                         (list 60.6486 -156.919) 
                         (list 60.6486 -156.9) 
                         (list 60.6301 -156.05) 
                         (list 61.6583 -155.952) 
                         (list 61.5428 -155.945) 
                         (list 61.3702 -155.92) 
                         (list 61.1666 -155.914) 
                         (list 60.9508 -155.902) 
                         "c"
         )
        (command "pline" (list 68.1484 -158.004) "w" 0 0 
                         (list 68.1792 -157.942) 
                         (list 68.1546 -157.862) 
                         (list 67.9942 -157.837) 
                         (list 67.9511 -157.763) 
                         (list 67.9511 -157.622) 
                         (list 67.9326 -157.511) 
                         (list 67.9079 -157.369) 
                         (list 67.8709 -157.252) 
                         (list 67.7784 -157.147) 
                         (list 67.6797 -157.079) 
                         (list 67.5194 -156.993) 
                         (list 67.359 -156.956) 
                         (list 67.285 -156.931) 
                         (list 67.1185 -156.919) 
                         (list 67.0075 -156.9) 
                         (list 66.989 -156.894) 
                         (list 67.0877 -156.882) 
                         (list 67.2233 -156.87) 
                         (list 67.4145 -156.845) 
                         (list 67.5749 -156.808) 
                         (list 67.7599 -156.746) 
                         (list 67.9202 -156.641) 
                         (list 67.9942 -156.543) 
                         (list 68.0682 -156.358) 
                         (list 68.0374 -156.228) 
                         (list 67.9449 -156.124) 
                         (list 67.8277 -156.05) 
                         (list 67.8197 -156.046) 
                         (list 67.1099 -156.396) 
                         (list 67.1136 -156.611) 
                         (list 67.0889 -156.685) 
                         (list 67.0642 -156.715) 
                         (list 66.9964 -156.777) 
                         (list 66.9347 -156.789) 
                         (list 66.8669 -156.802) 
                         (list 66.7004 -156.808) 
                         (list 66.2995 -156.796) 
                         (list 66.2625 -156.765) 
                         (list 66.2748 -156.044) 
                         (list 66.2995 -156.025) 
                         (list 66.8545 -156.025) 
                         (list 66.9594 -156.037) 
                         (list 67.021 -156.074) 
                         (list 67.0519 -156.117) 
                         (list 67.0704 -156.173) 
                         (list 67.0889 -156.21) 
                         (list 67.1074 -156.247) 
                         (list 67.1099 -156.396) 
                         (list 67.8197 -156.046) 
                         (list 67.6427 -155.976) 
                         (list 67.5872 -155.957) 
                         (list 67.2788 -155.92) 
                         (list 67.137 -155.92) 
                         (list 66.8841 -155.896) 
                         (list 66.4339 -155.883) 
                         (list 65.1141 -155.896) 
                         (list 65.0648 -155.902) 
                         (list 65.0586 -156.013) 
                         (list 65.1141 -156.025) 
                         (list 65.4225 -156.031) 
                         (list 65.441 -157.862) 
                         (list 65.1326 -157.856) 
                         (list 65.1388 -157.554) 
                         (list 65.1388 -157.474) 
                         (list 65.1635 -157.461) 
                         (list 65.1511 -157.289) 
                         (list 65.108 -157.276) 
                         (list 64.9846 -157.27) 
                         (list 64.923 -157.424) 
                         (list 64.849 -157.56) 
                         (list 64.7256 -157.683) 
                         (list 64.6331 -157.763) 
                         (list 64.5529 -157.794) 
                         (list 64.4111 -157.825) 
                         (list 64.2692 -157.874) 
                         (list 63.9917 -157.874) 
                         (list 63.4872 -157.868) 
                         (list 63.4564 -157.831) 
                         (list 63.4502 -156.974) 
                         (list 63.5797 -157.005) 
                         (list 63.7216 -157.03) 
                         (list 63.8819 -157.061) 
                         (list 64.0238 -157.11) 
                         (list 64.0731 -157.184) 
                         (list 64.1101 -157.258) 
                         (list 64.1163 -157.381) 
                         (list 64.1471 -157.4) 
                         (list 64.3075 -157.406) 
                         (list 64.3198 -157.381) 
                         (list 64.3136 -156.475) 
                         (list 64.2828 -156.463) 
                         (list 64.1348 -156.469) 
                         (list 64.104 -156.487) 
                         (list 64.0916 -156.567) 
                         (list 64.0793 -156.629) 
                         (list 64.0546 -156.697) 
                         (list 63.993 -156.734) 
                         (list 63.9251 -156.789) 
                         (list 63.8943 -156.814) 
                         (list 63.7648 -156.826) 
                         (list 63.6784 -156.833) 
                         (list 63.4564 -156.833) 
                         (list 63.4564 -156.025) 
                         (list 63.7586 -156.019) 
                         (list 63.9251 -156.031) 
                         (list 64.1718 -156.031) 
                         (list 64.2951 -156.056) 
                         (list 64.4062 -156.081) 
                         (list 64.4925 -156.117) 
                         (list 64.5727 -156.185) 
                         (list 64.6652 -156.29) 
                         (list 64.7268 -156.352) 
                         (list 64.7885 -156.432) 
                         (list 64.844 -156.469) 
                         (list 64.9242 -156.481) 
                         (list 65.0044 -156.469) 
                         (list 65.0044 -156.37) 
                         (list 65.0044 -155.896) 
                         (list 62.2846 -155.902) 
                         (list 62.2723 -155.933) 
                         (list 62.2785 -156.007) 
                         (list 62.3031 -156.044) 
                         (list 62.6115 -156.044) 
                         (list 62.6115 -157.856) 
                         (list 62.2415 -157.868) 
                         (list 62.2291 -157.911) 
                         (list 62.223 -157.985) 
                         (list 62.2723 -157.998) 
                         (list 66.7065 -157.985) 
                         (list 66.725 -157.961) 
                         (list 66.7189 -157.874) 
                         (list 66.7004 -157.856) 
                         (list 66.2995 -157.85) 
                         (list 66.281 -156.956) 
                         (list 66.2995 -156.937) 
                         (list 66.5215 -156.95) 
                         (list 66.6448 -156.962) 
                         (list 66.7374 -156.993) 
                         (list 66.836 -157.042) 
                         (list 66.8915 -157.091) 
                         (list 66.947 -157.19) 
                         (list 66.9779 -157.246) 
                         (list 66.9902 -157.344) 
                         (list 67.0087 -157.486) 
                         (list 67.0149 -157.603) 
                         (list 67.0581 -157.757) 
                         (list 67.1259 -157.825) 
                         (list 67.2246 -157.905) 
                         (list 67.3664 -157.967) 
                         (list 67.5329 -158.01) 
                         (list 67.6254 -158.028) 
                         (list 68.1435 -158.016) 
                         "c"
         )
  )
