(defun set_var ()
  (setq osnap_old (getvar "osmode"))
  (setq orthomode_old (getvar "orthomode"))
  (setvar "osmode" 0)
  (setvar "orthomode" 0)
  (list osnap_old orthomode_old)
)

(defun c:Widen ()
  (set_var)
  (prompt "\This program ONLY widen the entity LINE and ARC")
  (getstring "/Press blank key continue")
  (setq	layer_name
	 (strcase (getstring "请键入层名(直接回车将处理所有层):"))
  )
  (while (and (not (setq found (tblsearch "LAYER" layer_name)))
	      (/= layer_name "")
	 )
    (setq layer_name (getstring "请键入层名(直接回车将处理所有层):"))
  )
  (if found
    (progn
      (get_wid layer_name)
    )
    (progn
      (setq layer_name_lst nil)
      (setq layer_name (cdadr (tblnext "LAYER" T)))
      (while layer_name
	(setq layer_name_lst
	       (append layer_name_lst (list layer_name))
	)
	(setq layer_name (cdadr (tblnext "LAYER")))
      )
      (setq I_th 0)
      (setq layer_name (nth i_th layer_name_lst))
      (while layer_name
	(if (/= layer_name "PROBLEM")
	  (progn
	    (get_wid layer_name)
	  )
	)
	(setq i_th (+ i_th 1))
	(setq layer_name (nth i_th layer_name_lst))
      )
    )
  )
  (command "zoom" "e")
)
(defun get_wid (lay_name)
  (setq width "")
  (while (= width "")
    (setq width (getstring (strcat "输入 " lay_name "层线条宽度：")))
    (if	(<= (setq width (atof width)) 0)
      (setq width "")
    )
  )
  (setq cir_add (getstring "/是否在线端加圆Y/N(Y)"))
  (setq cir_add (strcase cir_add))
  (if (= cir_add "")
    (setq cir_add "Y")
  )
  (widen_line lay_name (/ width 2) cir_add)
  (widen_arc lay_name (/ width 2) cir_add)
)
(defun get_dt_vl (item dt)
  (cdr (assoc item dt))
)
(defun widen_line (lay_name width cir_add)
  (setq ss (ssget "x" (list (cons 0 "line") (cons 8 lay_name))))
  (if ss
    (progn

      (setq cnt_all (sslength ss))
      (setq cnt 0)
      (command "layer" "M" lay_name "")
      (while (< cnt cnt_all)
	(setq l_dt (entget (ssname ss cnt)))
	(setq stt_pnt (get_dt_vl 10 l_dt))
	(setq end_pnt (get_dt_vl 11 l_dt))
	(setq agl (angle stt_pnt end_pnt))
	(setq x0 (car stt_pnt))
	(setq y0 (cadr stt_pnt))
	(setq fst_pnt (list (+ x0 (* width (sin agl)))
			    (- y0 (* width (cos agl)))
		      )
	)
	(setq fth_pnt (list (- x0 (* width (sin agl)))
			    (+ y0 (* width (cos agl)))
		      )
	)
	(setq x0 (car end_pnt))
	(setq y0 (cadr end_pnt))
	(setq scd_pnt (list (+ x0 (* width (sin agl)))
			    (- y0 (* width (cos agl)))
		      )
	)
	(setq thd_pnt (list (- x0 (* width (sin agl)))
			    (+ y0 (* width (cos agl)))
		      )
	)
	(if (= cir_add "Y")
	  (command "pline" fst_pnt scd_pnt "a" thd_pnt "l" fth_pnt "a" "cl" "")
	  (command "pline" fst_pnt scd_pnt thd_pnt fth_pnt "c" "")
	  )
	(entdel (get_dt_vl -1 l_dt))
	(setq cnt (1+ cnt))
      )
    )
  )

)

(defun widen_arc (lay_name width cir_add)
  (setq ss (ssget "x" (list (cons 0 "arc") (cons 8 lay_name))))
  (if ss
    (progn
      (setq cnt_all (sslength ss))
      (setq cnt 0)
      (command "layer" "M" lay_name "")
      (while (< cnt cnt_all)
	(setq l_dt (entget (ssname ss cnt)))
	(setq center (get_dt_vl 10 l_dt))
	(setq rad (get_dt_vl 40 l_dt))
	(setq st_agl (get_dt_vl 50 l_dt))
	(setq end_agl (get_dt_vl 51 l_dt))
	(setq ent_dt (list
		       (cons 0 "arc")
		       (cons 10 center)
		       (cons 40 (- rad width))
		       (cons 50 st_agl)
		       (cons 51 end_agl)
		     )
	)
	(entmake ent_dt)
	(setq ent_dt (subst (cons 40 (+ rad width))
			    (cons 40 (- rad width))
			    ent_dt
		     )
	)
	(entmake ent_dt)
	(setq c_x (car center))
	(setq c_y (cadr center))
	(setq
	  fst_pnt (list	(+ c_x (* (cos st_agl) (- rad width)))
			(+ c_y (* (sin st_agl) (- rad width)))
		  )
	  scd_pnt (list	(+ c_x (* (cos st_agl) (+ rad width)))
			(+ c_y (* (sin st_agl) (+ rad width)))
		  )
	  thd_pnt (list	(+ c_x (* (cos end_agl) (- rad width)))
			(+ c_y (* (sin end_agl) (- rad width)))
		  )
	  fth_pnt (list	(+ c_x (* (cos end_agl) (+ rad width)))
			(+ c_y (* (sin end_agl) (+ rad width)))
		  )
	)
	(setq mid_pt (list (/ (+ (car fst_pnt) (car thd_pnt)) 2)
			   (/ (+ (cadr fst_pnt) (cadr thd_pnt)) 2)
		     )
	)
	(entmake
	  (list (cons 0 "line") (cons 10 fst_pnt) (cons 11 scd_pnt))
	)
	(entmake
	  (list (cons 0 "line") (cons 10 thd_pnt) (cons 11 fth_pnt))
	)
	(setq ent_sel (ssget "CP" (list fst_pnt scd_pnt fth_pnt thd_pnt)))
	
	(command "Pedit" "L" "Y" "J" ent_sel "" "")
	(if (= cir_add "Y")
	  (progn
	    (setq
	      mid_pnt (list (/ (+ (car fst_pnt) (car scd_pnt)) 2)
			    (/ (+ (cadr fst_pnt) (cadr scd_pnt)) 2)
		      )
	    )
	    (command "circle" mid_pnt width)
	    (setq
	      mid_pnt (list (/ (+ (car thd_pnt) (car fth_pnt)) 2)
			    (/ (+ (cadr thd_pnt) (cadr fth_pnt)) 2)
		      )
	    )
	    (command "circle" mid_pnt width)
	  )
	)
	(entdel (get_dt_vl -1 l_dt))
	(setq cnt (1+ cnt))
      )
    )
  )
)
(prompt "\Enter 'WIDEN' to run!")
