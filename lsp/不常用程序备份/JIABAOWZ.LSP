(defun set_var ()
  (setq osnap_old (getvar "osmode"))
  (setq orthomode_old (getvar "orthomode"))
  (setvar "osmode" 0)
  (setvar "orthomode" 0)
  (list osnap_old orthomode_old)
)
(defun get_dt_vl (item dt)
  (cdr (assoc item dt))
)
(defun c:wz ()
  (setq xn (getreal "\n X方向的排版个数:"))
  (setq yn (getreal "\n Y方向的排版个数:"))
  (setq x_val (getreal "\n X方向的排版尺寸:"))
  (setq y_val (getreal "\n Y方向的排版尺寸:"))
  (prompt "请选取要排版的文字!")
  (setq t_ss (ssget))
  (setq t_name (ssname t_ss 0))
  (setq t_detail (entget t_name))
  (setq t_h (get_dt_vl 40 t_detail))
  (setq t_w (get_dt_vl 1 t_detail))
  (setq f_point (cdr (assoc 10 t_detail)))
  (setq ang (getangle "\n 旋转角度: (180/0)"))
  (setq angl (* 180 (/ ang pi)))
  (setq x_f (car f_point))
  (setq y_f (cadr f_point))
  (setq xm (fix xn))
  (setq ym (fix yn))
  (command "-style" "black" "arial" t_h t_w "" "" "")
  (setq x1_f x_f)
  (setq y1_f y_f)
  (setq n1 1)
  (repeat ym
    (setq m n1)
    (repeat xm
      (setq zf m)
      (if (= angl 180)
	(progn
	  (command "text" f_point angl zf)
	  (setq l (entlast))
	  (command "mirror"
		   l
		   ""
		   (list x1_f y1_f)
		   (list x1_f (+ y1_f 1))
		   "y"
	  )
	)
	(command "text" f_point angl zf)
      )
      (setq x1_f (+ x1_f x_val))
      (setq f_point (list x1_f y1_f))
      (setq n1 m)
      (setq m (+ m 1))
    )
    (setq x1_f x_f)
    (setq y1_f (+ y1_f y_val))
    (setq f_point (list x1_f y1_f))
    (setq n1 (+ n1 1))
  )
)
