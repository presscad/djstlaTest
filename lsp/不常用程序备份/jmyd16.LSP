(defun c:jmyd ()
  (defun apr_ofst (ss_lwpl x_cpt y_cpt)
    (if	ss_lwpl
      (progn
	(setq ss_cnt (sslength ss_lwpl))
	(setq i_loop 0)
	(while (< i_loop ss_cnt)
	  (setq pl_dt (entget (ssname ss_lwpl i_loop)))
	  (setq cx 0)
	  (setq cy 0)
	  (setq cnt 0)
	  (setq dt pl_dt)
	  (while pl_dt
	    (if	(= (caar pl_dt) 10)
	      (progn
		(setq cx (+ (cadar pl_dt) cx))
		(setq cy (+ (caddar pl_dt) cy))
		(setq cnt (1+ cnt))
	      )
	    )
	    (setq pl_dt (cdr pl_dt))
	  )
	  (setq cx (/ cx cnt))
	  (setq cy (/ cy cnt))
	  (setq pl_dt dt)
	  (setq dt nil)
	  (while pl_dt
	    (if	(/= (caar pl_dt) 10)
	      (setq dt (append dt (list (car pl_dt))))
	      (progn
		(setq ofst_x (cadar pl_dt))
		(setq ofst_y (caddar pl_dt))
		(if (> ofst_x cx)
		  (setq ofst_x (- ofst_x x_cpt))
		  (setq ofst_x (+ ofst_x x_cpt))
		)
		(if (> ofst_y cy)
		  (setq ofst_y (- ofst_y y_cpt))
		  (setq ofst_y (+ ofst_y y_cpt))
		)
		(setq dt
		       (append dt (list (cons 10 (list ofst_x ofst_y 0))))
		)
	      )
	    )
	    (setq pl_dt (cdr pl_dt))
	  )
	  (entmod dt)
	  (setq i_loop (1+ i_loop))
	)
      )
    )
  )
   (defun scale (ss_lwpl ke)
    (if	ss_lwpl
      (progn
	(setq ss_cnt (sslength ss_lwpl))
	(setq i_loop 0)
	(while (< i_loop ss_cnt)
	  (setq pl_dt (entget (ssname ss_lwpl i_loop)))
	  (setq dt nil)
	  (while pl_dt
	    (if	(/= (caar pl_dt) 10)
	      (setq dt (append dt (list (car pl_dt))))
	      (progn
		(setq scl_x (cadar pl_dt))
		(setq scl_y (* (caddar pl_dt) ke))
		(setq
		  dt (append dt (list (cons 10 (list scl_x scl_y 0))))
		)
	      )
	    )
	    (setq pl_dt (cdr pl_dt))
	  )
	  (setq dt (subst (cons 8 "aprok") (assoc 8 dt) dt))
	  (entmake dt)
	  (setq i_loop (1+ i_loop))
	)
      )
    )    
  )
   (defun mark() 
        (command "pline" "-227.0,-213.341" "w" 0 0  "-227.0,-268.8" "227.0,-268.8" "227.0,-213.341" "225.0,-213.341" "225.0,-266.8" "-225.0,-266.8" "-225.0,-213.341" "c" )
        (command "pline" "-225.0,235.05" "w" 0 0  "-225.0,268.2" "225.0,268.2" "225.0,235.05" "227.0,235.05" "227.0,270.2" "225.0,270.2" "-227.0,270.2" "-227.0,235.05" "c" )
        (command "pline" "225.0,-266.8" "w" 0 0  "225.0,-266.75" "-225.0,-266.75" "-225.0,-266.8" "c" )
        (command "pline" "-225.0,-265.85" "w" 0 0  "225.0,-265.85" "225.0,-265.75" "-225.0,-265.75" "c" )
        (command "pline" "225.0,-264.75" "w" 0 0  "-225.0,-264.75" "-225.0,-264.85" "225.0,-264.85" "c" )
        (command "pline" "-225.0,-263.85" "w" 0 0  "225.0,-263.85" "225.0,-263.75" "-225.0,-263.75" "c" )
        (command "pline" "-225.0,-262.85" "w" 0 0  "225.0,-262.85" "225.0,-262.75" "-225.0,-262.75" "c" )
        (command "pline" "225.0,-261.75" "w" 0 0  "-225.0,-261.75" "-225.0,-261.85" "225.0,-261.85" "c" )
        (command "pline" "-225.0,-260.85" "w" 0 0  "225.0,-260.85" "225.0,-260.75" "-225.0,-260.75" "c" )
        (command "pline" "225.0,-259.75" "w" 0 0  "-225.0,-259.75" "-225.0,-259.85" "225.0,-259.85" "c" )
        (command "pline" "-225.0,-258.85" "w" 0 0  "225.0,-258.85" "225.0,-258.75" "-225.0,-258.75" "c" )
        (command "pline" "-225.0,-257.85" "w" 0 0  "225.0,-257.85" "225.0,-257.75" "-225.0,-257.75" "c" )
        (command "pline" "225.0,-248.8" "w" 0 0  "-225.0,-248.8" "-225.0,-245.8" "225.0,-245.8" "c" )
        (command "pline" "-225.0,259.15" "w" 0 0  "225.0,259.15" "225.0,259.25" "-225.0,259.25" "c" )
        (command "pline" "225.0,260.25" "w" 0 0  "-225.0,260.25" "-225.0,260.15" "225.0,260.15" "c" )
        (command "pline" "225.0,261.25" "w" 0 0  "-225.0,261.25" "-225.0,261.15" "225.0,261.15" "c" )
        (command "pline" "-225.0,262.15" "w" 0 0  "225.0,262.15" "225.0,262.25" "-225.0,262.25" "c" )
        (command "pline" "-225.0,263.15" "w" 0 0  "225.0,263.15" "225.0,263.25" "-225.0,263.25" "c" )
        (command "pline" "225.0,264.25" "w" 0 0  "-225.0,264.25" "-225.0,264.15" "225.0,264.15" "c" )
        (command "pline" "225.0,265.25" "w" 0 0  "-225.0,265.25" "-225.0,265.15" "225.0,265.15" "c" )
        (command "pline" "-225.0,266.15" "w" 0 0  "225.0,266.15" "225.0,266.25" "-225.0,266.25" "c" )
        (command "pline" "-225.0,267.15" "w" 0 0  "225.0,267.15" "225.0,267.25" "-225.0,267.25" "c" )
        (command "pline" "-225.0,268.15" "w" 0 0  "225.0,268.15" "225.0,268.2" "-225.0,268.2" "c" )
        (command "pline" "199.2,-2.125" "w" 0 0  "199.2,7.875" "200.5,7.875" "200.5,-2.125" "c" )
        (command "pline" "-199.2,-2.125" "w" 0 0  "-199.2,7.875" "-200.5,7.875" "-200.5,-2.125" "c" )
        (command "pline" "-199.2,-201.8" "w" 0 0  "-199.2,-191.8" "-200.5,-191.8" "-200.5,-201.8" "c" )
        (command "pline" "199.2,-201.8" "w" 0 0  "199.2,-191.8" "200.5,-191.8" "200.5,-201.8" "c" )
        (command "pline" "200.5,203.2" "w" 0 0  "204.85,203.2" "204.85,201.9" "200.5,201.9" "200.5,197.55" "199.2,197.55" "199.2,201.9" "194.85,201.9" "194.85,203.2" "199.2,203.2" "199.2,207.55" "200.5,207.55" "c" )
        (command "pline" "-200.5,203.2" "w" 0 0  "-204.85,203.2" "-204.85,201.9" "-200.5,201.9" "-200.5,197.55" "-199.2,197.55" "-199.2,201.9" "-194.85,201.9" "-194.85,203.2" "-199.2,203.2" "-199.2,207.55" "-200.5,207.55" "c" )
  )
  (setq ke 0.987)
  (setq ce 0.2)
  (setq cf 0.2)
  (getstring (strcat "请确认系数是：Ke=" (rtos ke) "; Ce=" (rtos ce) "; Cf=" (rtos  cf)))
  (command "osnap" "off")
  (command "ortho" "off")
  (command "layer" "Thaw" "*" "unlock" "*" "ON" "*" "")
  (command "zoom" "all")
  (setq dim_ent (ssget "x" (list (cons 0 "dim*"))))
  (if dim_ent
    (command "erase" dim_ent "")
  )
  (setq
    dim_ent (ssget "x" (list (cons 8 "0") (cons 10 '(0.0 0.0 0.0))(cons 0 "*polyline")))
  )
  (if (= (sslength dim_ent) 1)
    (command "move" "all" "" "0,0" "-7,-8")
    (progn
      (getstring "0层的ITO图形异常,自动程序无法运行!")
      (exit)
    )
  )
  (command "zoom" "all")
  (setq dim_ent (ssget "_W" '(-10 -12) '(10 12)))
  (command "layer" "m" "aprtmp" "color" "red" "" "")
  (command "change" "all" "r" dim_ent "" "p" "la" "aprtmp" "")
  (command "scale" "all" "" "0,0" "25.4")
  (command "zoom" "all")
  (command "layer" "m" "aprok" "color" "green" "" "")
  (setq dim_plus (ssget "x" (list (cons 0 "*polyline") (cons 8 "rel"))))
  (setq dim_ent (ssget "x" (list (cons 8 "rel"))))
  (if (and dim_plus dim_ent)
    (if	(and (= (sslength dim_plus) (sslength dim_ent)))
      (progn	
      (scale dim_plus ke)
      (setq dim_ent (ssget "x" (list (cons 8 "aprok"))))
      (apr_ofst dim_ent (/ cf 2) (/ ce 2))
      )
      ;(command "change" dim_plus "" "p" "la" "aprok" "")
      (progn
	(getstring
	  "rel层应该只有非多义线实体,请先对rel层做完topl后再运行程序,请确认!"
	)
	(exit)
      )
    )
    (progn
      (getstring "rel层不存,或需要对rel层做过topl后再运行此程序!")
      (exit)
    )
  )
  (setq dim_plus (ssget "x" (list (cons 0 "*polyline") (cons 8 "dim"))))
  (setq dim_ent (ssget "x" (list (cons 8 "dim"))))
  (if (and dim_plus dim_ent)
    (if	(and (= (sslength dim_plus) 2) (= (sslength dim_ent) 2))
      (scale dim_plus ke )
      ;(command "change" dim_plus "" "p" "la" "aprok" "")
      (progn
	(getstring
	  "DIM层应该只有两个+号(polyline),程序检查到有所不同,请确认!"
	)
	(exit)
      )
    )
    (progn
      (getstring "dim层不存,或需要对dim层做过topl后再运行此程序!")
      (exit)
    )
  )
  (setq dim_plus (ssget "x" (list (cons 0 "*polyline") (cons 8 "dum"))))
  (setq dim_ent (ssget "x" (list (cons 8 "dum"))))
  (if (and dim_plus dim_ent)
    (if	( or (and (= (sslength dim_plus) 4) (= (sslength dim_ent) 4)) (and (= (sslength dim_plus) 6) (= (sslength dim_ent) 6)))
      (scale dim_plus ke )
      ;(command "change" dim_plus "" "p" "la" "aprok" "")
      (progn
	(getstring
	  "DIM层应该只有4个dum多义线,程序检查到有所不同,请确认!"
	)
	(exit)
      )
    )
    (progn
      (getstring "dum层不存,或需要对rel层做过topl后再运行此程序!")
      (exit)
    )
  )
  (setq dim_plus (ssget "x" (list (cons 0 "*text") (cons 8 "dim2"))))
  (if dim_plus
     (if (= (sslength dim_plus) 1)
       (progn
	 (setq text_dt (entget (ssname dim_plus 0)))
	 (setq text_dt (assoc 1 text_dt))
	 (setq text_dt (cdr text_dt))
	 (setq c_date (getvar "cdate"))
	 (setq text_dt (strcat text_dt "  QINGYI " (itoa (fix c_date))))
	 (setq text_dt (list (cons 0 "text")(cons 1 text_dt) (cons 10 '(-118 -234 0)) (cons 40 8) (cons 8 "aprok")))
	 (entmake text_dt)
	 )
       )
    )
  (command "layer" "lock" "aprok" "" "")
  (command "change" "all" "" "p" "la" "aprtmp" "")
  (command "layer" "unlock" "aprok" "lock" "aprtmp" "m" "0" "" "")
  (mark)
  (command "change" "all" "" "p" "la" "0" "")
  (command "layer" "off" "aprtmp" "" "")
  (command "purge" "all" "" "N")
  (command "purge" "all" "" "N")
  (command "purge" "all" "" "N")
  (command "purge" "all" "" "N")
  (command "purge" "all" "" "N")
(getstring "\n处理完成! 原始图形放在aprtmp层供自检用,请检查中间+的对位")
)
(getstring "\n请先删除图纸空间一次,再运行jmyd")
