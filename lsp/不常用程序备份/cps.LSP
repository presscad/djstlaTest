(defun c:cps ()
  (defun get_dt_vl (item dt)
    (cdr (assoc item dt))
  )
  (command "zoom" "e")
  (setq cnt 0)
  (initget 1)
  (setq cps_val_1 (/ (getreal "/n请输入0.5-1.5um的线的补偿：") 2))
  (initget 1)
  (setq cps_val_2 (/ (getreal "/n请输入1.5-2.5um的线的补偿：") 2))
  (initget 1)
  (setq cps_val_3 (/ (getreal "/n请输入2.5-3.5um的线的补偿：") 2))
  (setq
    s_ofst (ssget "x"
		  (list (cons 0 "lwpolyline") (cons 70 1) (cons 90 4))
	   )
  )
  (if s_ofst
    (while (> (sslength s_ofst) 0)
      (setq s_name (ssname s_ofst 0))
      (setq lwp (entget s_name))
      (setq vt_cnt (get_dt_vl 90 lwp))
      (setq lwp_tmp lwp)
      (setq pt1 (get_dt_vl 10 lwp))
      (setq lwp (member (cons 10 pt1) lwp))
      (setq lwp (cdr lwp))
      (setq pt2 (get_dt_vl 10 lwp))
      (setq lwp (member (cons 10 pt2) lwp))
      (setq lwp (cdr lwp))
      (setq pt3 (get_dt_vl 10 lwp))
      (setq lwp (member (cons 10 pt3) lwp))
      (setq lwp (cdr lwp))
      (setq pt4 (get_dt_vl 10 lwp))
      (setq pt1_o pt1
	    pt2_o pt2
	    pt3_o pt3
	    pt4_o pt4
      )
      (setq flg nil)					;1um line 
      (if (and (equal (distance pt1 pt2) 0.001 0.0005)
	       (equal (distance pt3 pt4) 0.001 0.0005)
	  )
	(progn
	  (setq ofst_vl cps_val_1)
	  (if (equal (car pt1) (car pt2) 0.00001)
	    (if	(> (cadr pt1) (cadr pt2))
	      (setq
		pt1 (list (car pt1) (+ (cadr pt1) ofst_vl))
		pt2 (list (car pt2) (- (cadr pt2) ofst_vl))
		pt3 (list (car pt3) (- (cadr pt3) ofst_vl))
		pt4 (list (car pt4) (+ (cadr pt4) ofst_vl))
	      )
	      (setq
		pt1 (list (car pt1) (- (cadr pt1) ofst_vl))
		pt2 (list (car pt2) (+ (cadr pt2) ofst_vl))
		pt3 (list (car pt3) (+ (cadr pt3) ofst_vl))
		pt4 (list (car pt4) (- (cadr pt4) ofst_vl))
	      )
	    )
	    (if	(equal (cadr pt1) (cadr pt2) 0.00001)
	      (if (> (car pt1) (car pt2))
		(setq
		  pt1 (list (+ (car pt1) ofst_vl) (cadr pt1))
		  pt2 (list (- (car pt2) ofst_vl) (cadr pt2))
		  pt3 (list (- (car pt3) ofst_vl) (cadr pt3))
		  pt4 (list (+ (car pt4) ofst_vl) (cadr pt4))
		)
		(setq
		  pt1 (list (- (car pt1) ofst_vl) (cadr pt1))
		  pt2 (list (+ (car pt2) ofst_vl) (cadr pt2))
		  pt3 (list (+ (car pt3) ofst_vl) (cadr pt3))
		  pt4 (list (- (car pt4) ofst_vl) (cadr pt4))
		)
	      )
	    )
	  )
	)
      )
      (if (and (equal (distance pt2 pt3) 0.001 0.0005)
	       (equal (distance pt4 pt1) 0.001 0.0005)
	  )
	(progn
	  (setq ofst_vl cps_val_1)
	  (if (equal (car pt2) (car pt3) 0.00001)
	    (if	(> (cadr pt2) (cadr pt3))
	      (setq
		pt2 (list (car pt2) (+ (cadr pt2) ofst_vl))
		pt3 (list (car pt3) (- (cadr pt3) ofst_vl))
		pt4 (list (car pt4) (- (cadr pt4) ofst_vl))
		pt1 (list (car pt1) (+ (cadr pt1) ofst_vl))
	      )
	      (setq
		pt2 (list (car pt2) (- (cadr pt2) ofst_vl))
		pt3 (list (car pt3) (+ (cadr pt3) ofst_vl))
		pt4 (list (car pt4) (+ (cadr pt4) ofst_vl))
		pt1 (list (car pt1) (- (cadr pt1) ofst_vl))
	      )
	    )
	  )
	  (if (equal (cadr pt2) (cadr pt3) 0.00001)
	    (if	(> (car pt2) (car pt3))
	      (setq
		pt2 (list (+ (car pt2) ofst_vl) (cadr pt2))
		pt3 (list (- (car pt3) ofst_vl) (cadr pt3))
		pt4 (list (- (car pt4) ofst_vl) (cadr pt4))
		pt1 (list (+ (car pt1) ofst_vl) (cadr pt1))
	      )
	      (setq
		pt2 (list (- (car pt2) ofst_vl) (cadr pt2))
		pt3 (list (+ (car pt3) ofst_vl) (cadr pt3))
		pt4 (list (+ (car pt4) ofst_vl) (cadr pt4))
		pt1 (list (- (car pt1) ofst_vl) (cadr pt1))
	      )
	    )
	  )
	)
      )
      (if (> (distance pt1 pt1_o) 0.0001)
	(progn
	  (setq lwp (subst (cons 10 pt1) (cons 10 pt1_o) lwp_tmp))
	  (setq lwp (subst (cons 10 pt2) (cons 10 pt2_o) lwp))
	  (setq lwp (subst (cons 10 pt3) (cons 10 pt3_o) lwp))
	  (setq lwp (subst (cons 10 pt4) (cons 10 pt4_o) lwp))
	  (command "copy" s_name "" "0,0" "0,0")
	  (command "change" "L" "" "P" "LA" "0" "")
	  (entMod lwp)
	  (setq cnt (1+ cnt))
	  (setq flg T)
	)
      )

      (if (not flg)
	(progn
					;2um line 
	  (if (and (equal (distance pt1 pt2) 0.002 0.0005)
		   (equal (distance pt3 pt4) 0.002 0.0005)
	      )
	    (progn
	      (setq ofst_vl cps_val_2)
	      (if (equal (car pt1) (car pt2) 0.00001)
		(if (> (cadr pt1) (cadr pt2))
		  (setq
		    pt1	(list (car pt1) (+ (cadr pt1) ofst_vl))
		    pt2	(list (car pt2) (- (cadr pt2) ofst_vl))
		    pt3	(list (car pt3) (- (cadr pt3) ofst_vl))
		    pt4	(list (car pt4) (+ (cadr pt4) ofst_vl))
		  )
		  (setq
		    pt1	(list (car pt1) (- (cadr pt1) ofst_vl))
		    pt2	(list (car pt2) (+ (cadr pt2) ofst_vl))
		    pt3	(list (car pt3) (+ (cadr pt3) ofst_vl))
		    pt4	(list (car pt4) (- (cadr pt4) ofst_vl))
		  )
		)
		(if (equal (cadr pt1) (cadr pt2) 0.00001)
		  (if (> (car pt1) (car pt2))
		    (setq
		      pt1 (list (+ (car pt1) ofst_vl) (cadr pt1))
		      pt2 (list (- (car pt2) ofst_vl) (cadr pt2))
		      pt3 (list (- (car pt3) ofst_vl) (cadr pt3))
		      pt4 (list (+ (car pt4) ofst_vl) (cadr pt4))
		    )
		    (setq
		      pt1 (list (- (car pt1) ofst_vl) (cadr pt1))
		      pt2 (list (+ (car pt2) ofst_vl) (cadr pt2))
		      pt3 (list (+ (car pt3) ofst_vl) (cadr pt3))
		      pt4 (list (- (car pt4) ofst_vl) (cadr pt4))
		    )
		  )
		)
	      )
	    )
	  )
	  (if (and (equal (distance pt2 pt3) 0.002 0.0005)
		   (equal (distance pt4 pt1) 0.002 0.0005)
	      )
	    (progn
	      (setq ofst_vl cps_val_2)
	      (if (equal (car pt2) (car pt3) 0.00001)
		(if (> (cadr pt2) (cadr pt3))
		  (setq
		    pt2	(list (car pt2) (+ (cadr pt2) ofst_vl))
		    pt3	(list (car pt3) (- (cadr pt3) ofst_vl))
		    pt4	(list (car pt4) (- (cadr pt4) ofst_vl))
		    pt1	(list (car pt1) (+ (cadr pt1) ofst_vl))
		  )
		  (setq
		    pt2	(list (car pt2) (- (cadr pt2) ofst_vl))
		    pt3	(list (car pt3) (+ (cadr pt3) ofst_vl))
		    pt4	(list (car pt4) (+ (cadr pt4) ofst_vl))
		    pt1	(list (car pt1) (- (cadr pt1) ofst_vl))
		  )
		)
	      )
	      (if (equal (cadr pt2) (cadr pt3) 0.00001)
		(if (> (car pt2) (car pt3))
		  (setq
		    pt2	(list (+ (car pt2) ofst_vl) (cadr pt2))
		    pt3	(list (- (car pt3) ofst_vl) (cadr pt3))
		    pt4	(list (- (car pt4) ofst_vl) (cadr pt4))
		    pt1	(list (+ (car pt1) ofst_vl) (cadr pt1))
		  )
		  (setq
		    pt2	(list (- (car pt2) ofst_vl) (cadr pt2))
		    pt3	(list (+ (car pt3) ofst_vl) (cadr pt3))
		    pt4	(list (+ (car pt4) ofst_vl) (cadr pt4))
		    pt1	(list (- (car pt1) ofst_vl) (cadr pt1))
		  )
		)
	      )
	    )
	  )
	  (if (> (distance pt1 pt1_o) 0.0001)
	    (progn
	      (setq lwp (subst (cons 10 pt1) (cons 10 pt1_o) lwp_tmp))
	      (setq lwp (subst (cons 10 pt2) (cons 10 pt2_o) lwp))
	      (setq lwp (subst (cons 10 pt3) (cons 10 pt3_o) lwp))
	      (setq lwp (subst (cons 10 pt4) (cons 10 pt4_o) lwp))
	      (command "copy" s_name "" "0,0" "0,0")
	      (command "change" "L" "" "P" "LA" "0" "")
	      (entMod lwp)
	      (setq cnt (1+ cnt))
	      (setq flg T)
	    )
	  )
	)
      )

      (if (not flg)
	(progn
					;3um line 
	  (if (and (equal (distance pt1 pt2) 0.003 0.0005)
		   (equal (distance pt3 pt4) 0.003 0.0005)
	      )
	    (progn
	      (setq ofst_vl cps_val_3)
	      (if (equal (car pt1) (car pt2) 0.00001)
		(if (> (cadr pt1) (cadr pt2))
		  (setq
		    pt1	(list (car pt1) (+ (cadr pt1) ofst_vl))
		    pt2	(list (car pt2) (- (cadr pt2) ofst_vl))
		    pt3	(list (car pt3) (- (cadr pt3) ofst_vl))
		    pt4	(list (car pt4) (+ (cadr pt4) ofst_vl))
		  )
		  (setq
		    pt1	(list (car pt1) (- (cadr pt1) ofst_vl))
		    pt2	(list (car pt2) (+ (cadr pt2) ofst_vl))
		    pt3	(list (car pt3) (+ (cadr pt3) ofst_vl))
		    pt4	(list (car pt4) (- (cadr pt4) ofst_vl))
		  )
		)
		(if (equal (cadr pt1) (cadr pt2) 0.00001)
		  (if (> (car pt1) (car pt2))
		    (setq
		      pt1 (list (+ (car pt1) ofst_vl) (cadr pt1))
		      pt2 (list (- (car pt2) ofst_vl) (cadr pt2))
		      pt3 (list (- (car pt3) ofst_vl) (cadr pt3))
		      pt4 (list (+ (car pt4) ofst_vl) (cadr pt4))
		    )
		    (setq
		      pt1 (list (- (car pt1) ofst_vl) (cadr pt1))
		      pt2 (list (+ (car pt2) ofst_vl) (cadr pt2))
		      pt3 (list (+ (car pt3) ofst_vl) (cadr pt3))
		      pt4 (list (- (car pt4) ofst_vl) (cadr pt4))
		    )
		  )
		)
	      )
	    )
	  )
	  (if (and (equal (distance pt2 pt3) 0.003 0.0005)
		   (equal (distance pt4 pt1) 0.003 0.0005)
	      )
	    (progn
	      (setq ofst_vl cps_val_3)
	      (if (equal (car pt2) (car pt3) 0.00001)
		(if (> (cadr pt2) (cadr pt3))
		  (setq
		    pt2	(list (car pt2) (+ (cadr pt2) ofst_vl))
		    pt3	(list (car pt3) (- (cadr pt3) ofst_vl))
		    pt4	(list (car pt4) (- (cadr pt4) ofst_vl))
		    pt1	(list (car pt1) (+ (cadr pt1) ofst_vl))
		  )
		  (setq
		    pt2	(list (car pt2) (- (cadr pt2) ofst_vl))
		    pt3	(list (car pt3) (+ (cadr pt3) ofst_vl))
		    pt4	(list (car pt4) (+ (cadr pt4) ofst_vl))
		    pt1	(list (car pt1) (- (cadr pt1) ofst_vl))
		  )
		)
	      )
	      (if (equal (cadr pt2) (cadr pt3) 0.00001)
		(if (> (car pt2) (car pt3))
		  (setq
		    pt2	(list (+ (car pt2) ofst_vl) (cadr pt2))
		    pt3	(list (- (car pt3) ofst_vl) (cadr pt3))
		    pt4	(list (- (car pt4) ofst_vl) (cadr pt4))
		    pt1	(list (+ (car pt1) ofst_vl) (cadr pt1))
		  )
		  (setq
		    pt2	(list (- (car pt2) ofst_vl) (cadr pt2))
		    pt3	(list (+ (car pt3) ofst_vl) (cadr pt3))
		    pt4	(list (+ (car pt4) ofst_vl) (cadr pt4))
		    pt1	(list (- (car pt1) ofst_vl) (cadr pt1))
		  )
		)
	      )
	    )
	  )
	  (if (> (distance pt1 pt1_o) 0.0001)
	    (progn
	      (setq lwp (subst (cons 10 pt1) (cons 10 pt1_o) lwp_tmp))
	      (setq lwp (subst (cons 10 pt2) (cons 10 pt2_o) lwp))
	      (setq lwp (subst (cons 10 pt3) (cons 10 pt3_o) lwp))
	      (setq lwp (subst (cons 10 pt4) (cons 10 pt4_o) lwp))
	      (command "copy" s_name "" "0,0" "0,0")
	      (command "change" "L" "" "P" "LA" "0" "")
	      (entMod lwp)
	      (setq cnt (1+ cnt))
	      (setq flg T)
	    )
	  )
	)
      )
      (setq s_ofst (ssdel s_name s_ofst))
    )
  )
  (prompt (Strcat "/n总共有" (itoa cnt) "个实体被处理！"))
)
(prompt "/n输入命令 ofst")
