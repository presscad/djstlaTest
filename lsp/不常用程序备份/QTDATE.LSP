(defun c:qt () 
        (command "pline" (list 138.164 -159.61) "w" 0 0 
                         (list 139.391 -159.604) 
                         (list 139.397 -159.721) 
                         (list 139.064 -159.746) 
                         (list 138.885 -159.765) 
                         (list 138.034 -160.344) 
                         (list 139.305 -161.565) 
                         (list 139.416 -161.589) 
                         (list 139.749 -161.589) 
                         (list 139.767 -161.706) 
                         (list 138.009 -161.725) 
                         (list 137.997 -161.583) 
                         (list 138.305 -161.577) 
                         (list 137.374 -160.695) 
                         (list 137.368 -160.72) 
                         (list 137.35 -160.745) 
                         (list 137.368 -161.565) 
                         (list 137.405 -161.602) 
                         (list 137.757 -161.602) 
                         (list 137.769 -161.694) 
                         (list 137.738 -161.719) 
                         (list 136.116 -161.731) 
                         (list 136.104 -161.688) 
                         (list 136.104 -161.614) 
                         (list 136.159 -161.602) 
                         (list 136.492 -161.583) 
                         (list 136.474 -159.771) 
                         (list 136.19 -159.765) 
                         (list 136.104 -159.758) 
                         (list 136.091 -159.647) 
                         (list 136.172 -159.629) 
                         (list 137.744 -159.617) 
                         (list 137.744 -159.728) 
                         (list 137.72 -159.758) 
                         (list 137.374 -159.765) 
                         (list 137.35 -159.82) 
                         (list 137.35 -160.566) 
                         (list 137.38 -160.591) 
                         (list 138.552 -159.795) 
                         (list 138.527 -159.74) 
                         (list 138.225 -159.752) 
                         (list 138.145 -159.734) 
                         (list 138.145 -159.635) 
                         "c"
         )
        (command "pline" (list 133.914 -161.127) "w" 0 0 
                         (list 133.877 -161.188) 
                         (list 133.884 -161.725) 
                         (list 133.945 -161.762) 
                         (list 134.13 -161.762) 
                         (list 134.204 -161.712) 
                         (list 134.315 -161.657) 
                         (list 134.402 -161.7) 
                         (list 134.593 -161.749) 
                         (list 134.821 -161.786) 
                         (list 135.092 -161.793) 
                         (list 135.37 -161.786) 
                         (list 135.58 -161.743) 
                         (list 135.839 -161.626) 
                         (list 136.036 -161.466) 
                         (list 136.116 -161.386) 
                         (list 136.165 -161.25) 
                         (list 136.196 -161.084) 
                         (list 136.19 -160.899) 
                         (list 136.11 -160.745) 
                         (list 136.061 -160.652) 
                         (list 135.962 -160.584) 
                         (list 135.826 -160.51) 
                         (list 135.647 -160.449) 
                         (list 135.456 -160.393) 
                         (list 135.271 -160.35) 
                         (list 135.117 -160.326) 
                         (list 134.95 -160.295) 
                         (list 134.815 -160.264) 
                         (list 134.642 -160.239) 
                         (list 134.525 -160.196) 
                         (list 134.402 -160.171) 
                         (list 134.346 -160.141) 
                         (list 134.303 -160.085) 
                         (list 134.303 -160.023) 
                         (list 134.309 -159.974) 
                         (list 134.334 -159.912) 
                         (list 134.408 -159.857) 
                         (list 134.506 -159.808) 
                         (list 134.587 -159.783) 
                         (list 134.667 -159.771) 
                         (list 134.759 -159.74) 
                         (list 134.907 -159.74) 
                         (list 135.055 -159.74) 
                         (list 135.234 -159.765) 
                         (list 135.382 -159.826) 
                         (list 135.506 -159.869) 
                         (list 135.61 -160.005) 
                         (list 135.691 -160.122) 
                         (list 135.746 -160.196) 
                         (list 135.802 -160.221) 
                         (list 135.931 -160.221) 
                         (list 135.943 -160.184) 
                         (list 135.943 -159.654) 
                         (list 135.894 -159.629) 
                         (list 135.734 -159.641) 
                         (list 135.684 -159.697) 
                         (list 135.629 -159.715) 
                         (list 135.586 -159.715) 
                         (list 135.524 -159.715) 
                         (list 135.444 -159.678) 
                         (list 135.247 -159.623) 
                         (list 135.049 -159.604) 
                         (list 134.876 -159.598) 
                         (list 134.71 -159.604) 
                         (list 134.531 -159.635) 
                         (list 134.358 -159.709) 
                         (list 134.21 -159.771) 
                         (list 134.13 -159.851) 
                         (list 134.025 -159.949) 
                         (list 133.951 -160.067) 
                         (list 133.896 -160.239) 
                         (list 133.914 -160.387) 
                         (list 133.951 -160.547) 
                         (list 134.038 -160.64) 
                         (list 134.124 -160.695) 
                         (list 134.291 -160.775) 
                         (list 134.525 -160.856) 
                         (list 134.722 -160.905) 
                         (list 134.883 -160.923) 
                         (list 135.018 -160.93) 
                         (list 135.185 -160.954) 
                         (list 135.358 -160.985) 
                         (list 135.543 -161.034) 
                         (list 135.654 -161.102) 
                         (list 135.734 -161.188) 
                         (list 135.777 -161.269) 
                         (list 135.771 -161.392) 
                         (list 135.684 -161.515) 
                         (list 135.58 -161.565) 
                         (list 135.462 -161.626) 
                         (list 135.351 -161.651) 
                         (list 135.234 -161.657) 
                         (list 135.092 -161.675) 
                         (list 134.932 -161.669) 
                         (list 134.796 -161.645) 
                         (list 134.58 -161.602) 
                         (list 134.457 -161.521) 
                         (list 134.34 -161.441) 
                         (list 134.235 -161.336) 
                         (list 134.149 -161.219) 
                         (list 134.112 -161.152) 
                         "c"
         )
        (command "pline" (list 129.972 -161.762) "w" 0 0 
                         (list 130.983 -161.756) 
                         (list 132.55 -160.48) 
                         (list 132.18 -161.558) 
                         (list 132.044 -161.743) 
                         (list 132.981 -161.762) 
                         (list 133.654 -159.586) 
                         (list 132.704 -159.598) 
                         (list 130.095 -161.682) 
                         (list 129.972 -161.731) 
                         "c"
         )
        (command "pline" (list 113.868 -159.734) "w" 0 0 
                         (list 113.972 -159.715) 
                         (list 115.459 -159.709) 
                         (list 115.527 -159.752) 
                         (list 115.52 -159.845) 
                         (list 115.496 -159.857) 
                         (list 115.089 -159.857) 
                         (list 115.089 -161.164) 
                         (list 115.101 -161.244) 
                         (list 115.119 -161.38) 
                         (list 115.156 -161.454) 
                         (list 115.193 -161.571) 
                         (list 115.298 -161.657) 
                         (list 115.446 -161.7) 
                         (list 115.564 -161.706) 
                         (list 115.761 -161.719) 
                         (list 115.915 -161.706) 
                         (list 116.082 -161.688) 
                         (list 116.205 -161.657) 
                         (list 116.341 -161.608) 
                         (list 116.445 -161.503) 
                         (list 116.507 -161.373) 
                         (list 116.519 -161.312) 
                         (list 116.526 -161.145) 
                         (list 116.519 -160.8) 
                         (list 116.519 -159.943) 
                         (list 116.507 -159.888) 
                         (list 116.47 -159.863) 
                         (list 116.452 -159.851) 
                         (list 116.186 -159.863) 
                         (list 116.119 -159.832) 
                         (list 116.119 -159.721) 
                         (list 116.168 -159.715) 
                         (list 116.97 -159.703) 
                         (list 116.988 -159.758) 
                         (list 116.988 -159.826) 
                         (list 116.896 -159.857) 
                         (list 116.803 -159.869) 
                         (list 116.772 -159.919) 
                         (list 116.76 -159.968) 
                         (list 116.754 -160.03) 
                         (list 116.772 -161.281) 
                         (list 116.754 -161.398) 
                         (list 116.717 -161.472) 
                         (list 116.661 -161.565) 
                         (list 116.6 -161.638) 
                         (list 116.513 -161.688) 
                         (list 116.347 -161.756) 
                         (list 116.205 -161.805) 
                         (list 116.069 -161.836) 
                         (list 116.014 -161.848) 
                         (list 115.224 -161.867) 
                         (list 115.15 -161.854) 
                         (list 114.971 -161.83) 
                         (list 114.811 -161.799) 
                         (list 114.614 -161.743) 
                         (list 114.515 -161.688) 
                         (list 114.441 -161.663) 
                         (list 114.386 -161.608) 
                         (list 114.349 -161.54) 
                         (list 114.305 -161.46) 
                         (list 114.275 -161.343) 
                         (list 114.256 -161.17) 
                         (list 114.256 -160.979) 
                         (list 114.256 -159.919) 
                         (list 114.238 -159.863) 
                         (list 114.207 -159.857) 
                         (list 113.868 -159.863) 
                         (list 113.855 -159.814) 
                         "c"
         )
        (command "pline" (list 108.414 -162.105) "w" 0 0 
                         (list 113.597 -159.854) 
                         (list 113.628 -159.9) 
                         (list 113.597 -159.932) 
                         (list 112.202 -160.524) 
                         (list 112.194 -160.586) 
                         (list 110.432 -161.303) 
                         (list 110.401 -161.38) 
                         (list 108.5 -162.175) 
                         "c"
         )
        (command "pline" (list 108.718 -162.37) "w" 0 0 
                         (list 108.624 -162.292) 
                         (list 108.609 -162.276) 
                         (list 113.542 -160.157) 
                         (list 113.604 -160.157) 
                         (list 113.628 -160.204) 
                         (list 112.404 -160.718) 
                         (list 112.217 -160.781) 
                         (list 112.217 -160.851) 
                         (list 110.425 -161.575) 
                         (list 110.425 -161.638) 
                         "c"
         )
        (command "pline" (list 108.874 -162.448) "w" 0 0 
                         (list 113.472 -160.469) 
                         (list 113.527 -160.461) 
                         (list 113.558 -160.485) 
                         (list 112.217 -161.069) 
                         (list 112.225 -161.116) 
                         (list 110.464 -161.84) 
                         (list 110.471 -161.91) 
                         (list 109.17 -162.463) 
                         (list 109.201 -162.494) 
                         (list 109.03 -162.518) 
                         (list 108.96 -162.51) 
                         "c"
         )
        (command "pline" (list 109.131 -162.603) "w" 0 0 
                         (list 113.441 -160.773) 
                         (list 113.464 -160.781) 
                         (list 113.488 -160.804) 
                         (list 113.472 -160.843) 
                         (list 112.264 -161.342) 
                         (list 112.248 -161.373) 
                         (list 110.471 -162.12) 
                         (list 110.479 -162.167) 
                         (list 109.926 -162.424) 
                         (list 109.801 -162.448) 
                         (list 109.778 -162.471) 
                         (list 109.848 -162.487) 
                         (list 109.817 -162.518) 
                         (list 109.715 -162.51) 
                         (list 109.7 -162.51) 
                         (list 109.427 -162.642) 
                         (list 109.256 -162.681) 
                         (list 109.147 -162.611) 
                         "c"
         )
        (command "pline" (list 109.482 -162.744) "w" 0 0 
                         (list 113.301 -161.131) 
                         (list 113.316 -161.162) 
                         (list 113.332 -161.193) 
                         (list 112.241 -161.638) 
                         (list 112.225 -161.669) 
                         (list 111.048 -162.167) 
                         (list 110.464 -162.409) 
                         (list 110.456 -162.44) 
                         (list 110.456 -162.479) 
                         (list 110.479 -162.51) 
                         (list 110.323 -162.526) 
                         (list 109.731 -162.806) 
                         (list 109.622 -162.829) 
                         (list 109.575 -162.814) 
                         "c"
         )
        (command "pline" (list 109.84 -162.868) "w" 0 0 
                         (list 112.981 -161.528) 
                         (list 113.004 -161.505) 
                         (list 113.082 -161.49) 
                         (list 113.075 -161.536) 
                         (list 113.051 -161.583) 
                         (list 112.295 -161.895) 
                         (list 112.272 -161.98) 
                         (list 111.079 -162.471) 
                         (list 111.056 -162.479) 
                         (list 111.118 -162.51) 
                         (list 110.931 -162.51) 
                         (list 110.581 -162.65) 
                         (list 110.518 -162.658) 
                         (list 110.495 -162.713) 
                         (list 110.487 -162.767) 
                         (list 110.16 -162.907) 
                         (list 110.012 -162.907) 
                         "c"
         )
        (command "pline" (list 110.44 -162.915) "w" 0 0 
                         (list 110.51 -162.861) 
                         (list 112.708 -161.926) 
                         (list 112.732 -161.957) 
                         (list 112.7 -161.996) 
                         (list 112.435 -162.105) 
                         (list 112.295 -162.167) 
                         (list 112.287 -162.23) 
                         (list 111.757 -162.44) 
                         (list 111.703 -162.432) 
                         (list 111.711 -162.471) 
                         (list 111.773 -162.494) 
                         (list 111.602 -162.51) 
                         (list 110.627 -162.923) 
                         "c"
         )
        (command "pline" (list 110.043 -161.199) "w" 0 0 
                         (list 115.296 -158.979) 
                         (list 115.21 -158.901) 
                         (list 115.124 -158.862) 
                         (list 113.184 -159.703) 
                         (list 113.238 -159.742) 
                         (list 111.492 -160.49) 
                         (list 111.399 -160.56) 
                         (list 110.004 -161.168) 
                         "c"
         )
        (command "pline" (list 110.019 -160.911) "w" 0 0 
                         (list 110.121 -160.918) 
                         (list 115.038 -158.776) 
                         (list 114.961 -158.722) 
                         (list 114.836 -158.714) 
                         (list 113.191 -159.415) 
                         (list 113.23 -159.477) 
                         (list 111.43 -160.209) 
                         (list 111.391 -160.256) 
                         (list 111.298 -160.311) 
                         (list 110.027 -160.864) 
                         "c"
         )
        (command "pline" (list 110.097 -160.607) "w" 0 0 
                         (list 114.797 -158.605) 
                         (list 114.727 -158.535) 
                         (list 114.61 -158.527) 
                         (list 114.547 -158.542) 
                         (list 113.277 -159.111) 
                         (list 113.215 -159.15) 
                         (list 113.184 -159.22) 
                         (list 111.43 -159.945) 
                         (list 111.407 -159.991) 
                         (list 110.066 -160.56) 
                         "c"
         )
        (command "pline" (list 110.168 -160.272) "w" 0 0 
                         (list 110.269 -160.272) 
                         (list 110.386 -160.241) 
                         (list 114.516 -158.426) 
                         (list 114.392 -158.387) 
                         (list 114.275 -158.387) 
                         (list 113.168 -158.862) 
                         (list 113.168 -158.924) 
                         (list 111.391 -159.664) 
                         (list 111.36 -159.703) 
                         (list 111.266 -159.758) 
                         (list 110.144 -160.248) 
                         "c"
         )
        (command "pline" (list 110.323 -159.921) "w" 0 0 
                         (list 110.456 -159.89) 
                         (list 114.205 -158.293) 
                         (list 114.08 -158.254) 
                         (list 113.932 -158.239) 
                         (list 113.893 -158.246) 
                         (list 113.191 -158.558) 
                         (list 113.145 -158.667) 
                         (list 111.383 -159.392) 
                         (list 111.204 -159.501) 
                         (list 110.347 -159.867) 
                         (list 110.308 -159.906) 
                         "c"
         )
        (command "pline" (list 110.573 -159.532) "w" 0 0 
                         (list 110.635 -159.54) 
                         (list 113.784 -158.2) 
                         (list 113.643 -158.161) 
                         (list 113.464 -158.169) 
                         (list 113.129 -158.324) 
                         (list 113.152 -158.356) 
                         (list 111.391 -159.088) 
                         (list 111.383 -159.15) 
                         (list 110.573 -159.501) 
                         "c"
         )
        (command "pline" (list 110.978 -159.064) "w" 0 0 
                         (list 111.009 -159.088) 
                         (list 111.118 -159.049) 
                         (list 113.269 -158.145) 
                         (list 113.168 -158.122) 
                         (list 113.059 -158.122) 
                         (list 111.329 -158.846) 
                         (list 111.321 -158.901) 
                         (list 110.962 -159.049) 
                         "c"
         )
        (command "pline" (list 127.966 -161.638) "w" 0 0 
                         (list 127.917 -161.651) 
                         (list 127.923 -161.749) 
                         (list 127.985 -161.762) 
                         (list 129.551 -161.762) 
                         (list 129.594 -161.737) 
                         (list 129.594 -161.638) 
                         (list 129.514 -161.626) 
                         (list 129.163 -161.626) 
                         (list 129.144 -159.802) 
                         (list 129.508 -159.808) 
                         (list 129.57 -159.771) 
                         (list 129.576 -159.691) 
                         (list 129.551 -159.666) 
                         (list 129.496 -159.654) 
                         (list 128.225 -159.66) 
                         (list 127.664 -160.8) 
                         (list 127.639 -160.819) 
                         (list 127.06 -159.666) 
                         (list 125.672 -159.672) 
                         (list 125.66 -159.789) 
                         (list 125.715 -159.814) 
                         (list 126.085 -159.814) 
                         (list 126.091 -161.515) 
                         (list 126.079 -161.571) 
                         (list 126.048 -161.632) 
                         (list 125.956 -161.645) 
                         (list 125.863 -161.663) 
                         (list 125.863 -161.737) 
                         (list 125.876 -161.762) 
                         (list 126.708 -161.774) 
                         (list 126.739 -161.749) 
                         (list 126.739 -161.682) 
                         (list 126.714 -161.645) 
                         (list 126.369 -161.638) 
                         (list 126.332 -161.583) 
                         (list 126.307 -161.521) 
                         (list 126.289 -159.906) 
                         (list 126.307 -159.912) 
                         (list 127.165 -161.706) 
                         (list 127.214 -161.762) 
                         (list 127.405 -161.756) 
                         (list 128.281 -159.937) 
                         (list 128.312 -159.888) 
                         (list 128.336 -159.956) 
                         (list 128.342 -161.608) 
                         (list 128.336 -161.632) 
                         (list 128.009 -161.638) 
                         "c"
         )
        (command "pline" (list 117.148 -159.709) "w" 0 0 
                         (list 117.155 -159.832) 
                         (list 117.284 -159.839) 
                         (list 117.352 -159.851) 
                         (list 117.358 -161.657) 
                         (list 117.34 -161.682) 
                         (list 116.982 -161.682) 
                         (list 116.97 -161.706) 
                         (list 116.97 -161.786) 
                         (list 117.0 -161.805) 
                         (list 117.044 -161.817) 
                         (list 118.629 -161.811) 
                         (list 118.666 -161.786) 
                         (list 118.672 -161.7) 
                         (list 118.635 -161.663) 
                         (list 118.209 -161.657) 
                         (list 118.203 -160.948) 
                         (list 118.215 -160.88) 
                         (list 118.234 -160.856) 
                         (list 118.296 -160.856) 
                         (list 118.376 -160.849) 
                         (list 118.444 -160.849) 
                         (list 118.709 -160.843) 
                         (list 118.918 -160.837) 
                         (list 119.147 -160.843) 
                         (list 119.282 -160.812) 
                         (list 119.498 -160.775) 
                         (list 119.665 -160.714) 
                         (list 119.831 -160.615) 
                         (list 119.93 -160.517) 
                         (list 119.998 -160.406) 
                         (list 120.004 -160.332) 
                         (list 120.016 -160.227) 
                         (list 119.979 -160.116) 
                         (list 119.936 -160.023) 
                         (list 119.868 -159.937) 
                         (list 119.726 -159.863) 
                         (list 119.603 -159.802) 
                         (list 119.455 -159.771) 
                         (list 119.295 -159.752) 
                         (list 119.219 -159.747) 
                         (list 118.191 -159.845) 
                         (list 118.462 -159.839) 
                         (list 118.616 -159.826) 
                         (list 118.807 -159.839) 
                         (list 118.949 -159.888) 
                         (list 119.017 -159.968) 
                         (list 119.06 -160.067) 
                         (list 119.079 -160.178) 
                         (list 119.073 -160.313) 
                         (list 119.085 -160.424) 
                         (list 119.06 -160.523) 
                         (list 119.06 -160.547) 
                         (list 118.992 -160.665) 
                         (list 118.918 -160.702) 
                         (list 118.869 -160.714) 
                         (list 118.721 -160.714) 
                         (list 118.209 -160.714) 
                         (list 118.209 -160.695) 
                         (list 118.191 -159.845) 
                         (list 119.219 -159.747) 
                         (list 119.103 -159.74) 
                         (list 118.931 -159.715) 
                         (list 118.727 -159.709) 
                         (list 118.511 -159.697) 
                         "c"
         )
        (command "pline" (list 125.709 -161.799) "w" 0 0 
                         (list 125.74 -161.737) 
                         (list 125.715 -161.657) 
                         (list 125.555 -161.632) 
                         (list 125.512 -161.558) 
                         (list 125.512 -161.417) 
                         (list 125.493 -161.306) 
                         (list 125.469 -161.164) 
                         (list 125.432 -161.047) 
                         (list 125.339 -160.942) 
                         (list 125.24 -160.874) 
                         (list 125.08 -160.788) 
                         (list 124.92 -160.751) 
                         (list 124.846 -160.726) 
                         (list 124.679 -160.714) 
                         (list 124.568 -160.695) 
                         (list 124.55 -160.689) 
                         (list 124.648 -160.677) 
                         (list 124.784 -160.665) 
                         (list 124.975 -160.64) 
                         (list 125.136 -160.603) 
                         (list 125.321 -160.541) 
                         (list 125.481 -160.436) 
                         (list 125.555 -160.338) 
                         (list 125.629 -160.153) 
                         (list 125.598 -160.023) 
                         (list 125.506 -159.919) 
                         (list 125.388 -159.845) 
                         (list 125.38 -159.841) 
                         (list 124.671 -160.191) 
                         (list 124.674 -160.406) 
                         (list 124.65 -160.48) 
                         (list 124.625 -160.51) 
                         (list 124.557 -160.572) 
                         (list 124.495 -160.584) 
                         (list 124.428 -160.597) 
                         (list 124.261 -160.603) 
                         (list 123.86 -160.591) 
                         (list 123.823 -160.56) 
                         (list 123.835 -159.839) 
                         (list 123.86 -159.82) 
                         (list 124.415 -159.82) 
                         (list 124.52 -159.832) 
                         (list 124.582 -159.869) 
                         (list 124.613 -159.912) 
                         (list 124.631 -159.968) 
                         (list 124.65 -160.005) 
                         (list 124.668 -160.042) 
                         (list 124.671 -160.191) 
                         (list 125.38 -159.841) 
                         (list 125.203 -159.771) 
                         (list 125.148 -159.752) 
                         (list 124.839 -159.715) 
                         (list 124.698 -159.715) 
                         (list 124.445 -159.691) 
                         (list 123.995 -159.678) 
                         (list 122.675 -159.691) 
                         (list 122.625 -159.697) 
                         (list 122.619 -159.808) 
                         (list 122.675 -159.82) 
                         (list 122.983 -159.826) 
                         (list 123.002 -161.657) 
                         (list 122.693 -161.651) 
                         (list 122.699 -161.349) 
                         (list 122.699 -161.269) 
                         (list 122.724 -161.256) 
                         (list 122.712 -161.084) 
                         (list 122.669 -161.071) 
                         (list 122.545 -161.065) 
                         (list 122.484 -161.219) 
                         (list 122.41 -161.355) 
                         (list 122.286 -161.478) 
                         (list 122.194 -161.558) 
                         (list 122.114 -161.589) 
                         (list 121.972 -161.62) 
                         (list 121.83 -161.669) 
                         (list 121.552 -161.669) 
                         (list 121.048 -161.663) 
                         (list 121.017 -161.626) 
                         (list 121.011 -160.769) 
                         (list 121.14 -160.8) 
                         (list 121.282 -160.825) 
                         (list 121.443 -160.856) 
                         (list 121.584 -160.905) 
                         (list 121.634 -160.979) 
                         (list 121.671 -161.053) 
                         (list 121.677 -161.176) 
                         (list 121.708 -161.195) 
                         (list 121.868 -161.201) 
                         (list 121.88 -161.176) 
                         (list 121.874 -160.27) 
                         (list 121.843 -160.258) 
                         (list 121.695 -160.264) 
                         (list 121.665 -160.282) 
                         (list 121.652 -160.362) 
                         (list 121.64 -160.424) 
                         (list 121.615 -160.492) 
                         (list 121.554 -160.529) 
                         (list 121.486 -160.584) 
                         (list 121.455 -160.609) 
                         (list 121.325 -160.621) 
                         (list 121.239 -160.628) 
                         (list 121.017 -160.628) 
                         (list 121.017 -159.82) 
                         (list 121.319 -159.814) 
                         (list 121.486 -159.826) 
                         (list 121.732 -159.826) 
                         (list 121.856 -159.851) 
                         (list 121.967 -159.876) 
                         (list 122.053 -159.912) 
                         (list 122.133 -159.98) 
                         (list 122.226 -160.085) 
                         (list 122.287 -160.147) 
                         (list 122.349 -160.227) 
                         (list 122.405 -160.264) 
                         (list 122.485 -160.276) 
                         (list 122.565 -160.264) 
                         (list 122.565 -160.165) 
                         (list 122.565 -159.691) 
                         (list 119.845 -159.697) 
                         (list 119.833 -159.728) 
                         (list 119.839 -159.802) 
                         (list 119.864 -159.839) 
                         (list 120.172 -159.839) 
                         (list 120.172 -161.651) 
                         (list 119.802 -161.663) 
                         (list 119.79 -161.706) 
                         (list 119.784 -161.78) 
                         (list 119.833 -161.793) 
                         (list 124.267 -161.78) 
                         (list 124.286 -161.756) 
                         (list 124.28 -161.669) 
                         (list 124.261 -161.651) 
                         (list 123.86 -161.645) 
                         (list 123.842 -160.751) 
                         (list 123.86 -160.732) 
                         (list 124.082 -160.745) 
                         (list 124.205 -160.757) 
                         (list 124.298 -160.788) 
                         (list 124.397 -160.837) 
                         (list 124.452 -160.886) 
                         (list 124.508 -160.985) 
                         (list 124.539 -161.041) 
                         (list 124.551 -161.139) 
                         (list 124.569 -161.281) 
                         (list 124.576 -161.398) 
                         (list 124.619 -161.552) 
                         (list 124.687 -161.62) 
                         (list 124.785 -161.7) 
                         (list 124.927 -161.762) 
                         (list 125.094 -161.805) 
                         (list 125.186 -161.823) 
                         (list 125.704 -161.811) 
                         "c"
         )
   (command "style" "ht" "simhei.ttf" "" "" "" "" "" "")
   	(setq c_date (rtos (getvar "CDATE")))
	(setq c_date (strcat (substr c_date 1 4) "/" (substr c_date 5 2) "/" (substr c_date 7 2)))
   	(setq txt_dt (list (cons 0 "TEXT") (cons 1 c_date) (cons 10 (list 144 -161.7)) (cons 40 2) (cons 7 "ht")))
	(entmake txt_dt)
  )
