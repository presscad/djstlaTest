(defun c:draw_ckl ()
  (setq x_max 420)
  (setq y_max 328)
  (setq r 0.1675)
  (setq pv 1.03923)
  (setq ph 0.6)
  (setq i 0)
  (setq j 0)
					;(command "circle" (list 0 0) 0.1675)
  (while (< (* j ph) x_max)
    (while (< (* i pv) y_max)
      (command "circle" (list (* j ph) (* i pv)) r)
      (setq i (1+ i))
    )
    (setq i 0)
    (setq j (1+ j))
  )
)
