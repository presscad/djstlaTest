(defun CHANG()
  (setvar "OSMODE" 2)
  (setq pt1 (getpoint "\n点取第一列粒块一底边中点"))
  (setq pt2 (getpoint "\n点取第一列粒块一顶边中点"))
  (setq pt3 (getpoint "\n点取第一列粒块二底边中点"))
  (setq pt4 (getpoint "\n点取第一列粒块二顶边中点"))
  (setq pt5 (getpoint "\n点取第一列粒块三底边中点"))
;  (setq last1 (getpoint "\n点取第一列最上粒块顶边中点"))
  (setq pt6 (getpoint "\n点取第一行粒块一左边中点"))
  (setq pt7 (getpoint "\n点取第一行粒块一右边中点"))
  (setq pt8 (getpoint "\n点取第一行粒块二左边中点"))
  (setq pt9 (getpoint "\n点取第一行粒块二右边中点"))
  (setq pt10 (getpoint "\n点取第一行粒块三左边中点"))
;  (setq last2 (getpoint "\n点取第一行最右粒块右边中点"))
  (setq pt11 (getpoint "\n点取圆周上一点"))
  (setvar "OSMODE" 4)
  (setq pt12 (getpoint "\n点取圆弧中心点"))


  (setq e_input (abs (- (car (cdr pt1))
			(car (cdr pt2))
		     )
               	))  
  (setq g_input (abs (- (car (cdr pt2))
			(car (cdr pt3))
		     )
               	))  
  (setq h_input (abs (- (car (cdr pt4))
			(car (cdr pt5))
		     )
               	)) 
  (setq en_pi (getint "\n输入E方向粒数:"))
  (setq f_input (abs (- (car pt6)
			(car pt7)
		     )
               	)) 
  (setq i_input (abs (- (car pt7)
			(car pt8)
		     )
               	))  
  (setq j_input (abs (- (car pt9)
			(car pt10)
		     )
               	)) 
  (setq fn_pi (getint "\n输入F方向粒数:"))
  (setq r_input (distance pt11 pt12))
  (setvar "OSMODE" 0)

  (setq ke1 0.9770 ce1 0.3800 kf1 0.0000 cf1 0.3500)
  (setq e_pi (* ke1 (- e_input ce1)))
  (setq g_pi (* ke1 (+ g_input ce1)))
  (setq h_pi (* ke1 (+ h_input ce1)))
  (setq f_pi (- f_input (+ cf1 (* kf1 f_input))))
  (setq i_pi (+ i_input (+ cf1 (* kf1 f_input))))
  (setq j_pi (+ j_input (+ cf1 (* kf1 f_input))))
  (SETQ r_pi r_input)
    
  (command "layer" "n" "done" "")
  (setvar "CLAYER" "done")
  (command "layer" "c" "red" "done" "")
  (command "limits" (list -100 -100) (list 1000 800))
  (command "zoom" "a")

  ;Align the center of pi drawing with one of glass
   (setq glass_x 0 glass_y 0)
   (setq x_pitch (+ f_pi f_pi i_pi j_pi))
   (setq y_pitch (+ e_pi e_pi g_pi h_pi))
   (cond ( (and (= 0 (rem en_pi (fix (/ en_pi 2))))
                (= 0 (rem fn_pi (fix (/ fn_pi 2))))
	   ) 
           (setq ftotal_pi (- (* (/ fn_pi 2) x_pitch) j_pi)
                 etotal_pi (- (* (/ en_pi 2) y_pitch) h_pi)
           )             
         )
         ( (and (= 0 (rem en_pi (fix (/ en_pi 2)))) 
                (= 1 (rem fn_pi (fix (/ fn_pi 2))))
           ) 
           (setq ftotal_pi (+ (* (/ fn_pi 2) x_pitch) f_pi)
                 etotal_pi (- (* (/ en_pi 2) y_pitch) h_pi)
           )             
         )
         ( (and (= 1 (rem en_pi (fix (/ en_pi 2)))) 
                (= 0 (rem fn_pi (fix (/ fn_pi 2))))
           ) 
           (setq ftotal_pi (- (* (/ fn_pi 2) x_pitch) j_pi)
                 etotal_pi (+ (* (/ en_pi 2) y_pitch) e_pi)
           )             
         )
         ( (and (= 1 (rem en_pi (fix (/ en_pi 2)))) 
                (= 1 (rem fn_pi (fix (/ fn_pi 2))))
           ) 
           (setq ftotal_pi (+ (* (/ fn_pi 2) x_pitch) f_pi)
                 etotal_pi (+ (* (/ en_pi 2) y_pitch) e_pi)
           )             
         )
   )
   (setq origin_x (- glass_x (/ ftotal_pi 2))
         origin_y (- glass_y (/ etotal_pi 2))         
   )
   (print "Align the center of pi drawing with one of glass ok!")

  ;Draw a pi cell
  (setq p1 (list (+ r_pi origin_x) (+ 0 origin_y)) 
        p2 (list (+ (- f_pi r_pi) origin_x) (+ 0 origin_y ))
        p3 (list (+ f_pi origin_x) (+ r_pi origin_y))
        p4 (list (+ f_pi origin_x) (+ (- e_pi r_pi) origin_y)) 
        p5 (list (+ (- f_pi r_pi) origin_x) (+ e_pi origin_y))
        p6 (list (+ r_pi origin_x) (+ e_pi origin_y))
        p7 (list (+ 0 origin_x) (+ (- e_pi r_pi) origin_y))
        p8 (list (+ 0 origin_x) (+ r_pi origin_y))
        o1 (list (+ r_pi origin_x) (+ r_pi origin_y))
        o2 (list (+ (- f_pi r_pi) origin_x) (+ r_pi origin_y))
        o3 (list (+ (- f_pi r_pi) origin_x) (+ (- e_pi r_pi) origin_y)) 
        o4 (list (+ r_pi origin_x) (+ (- e_pi r_pi) origin_y))
  )
  (setq last_ss (entlast))
  (command "pline" p1 "w" 0 0 p2
                   "a" "r" r_pi p3
                   "l" p4
                   "a" "r" r_pi p5
                   "l" p6
                   "a" "r" r_pi p7
                   "l" p8
                   "a" "r" r_pi p1
                   ""
   )

  (setq ss1  (entnext last_ss))
  (command "array" ss1 "" "R" 2 2 (+ e_pi g_pi) (+ f_pi i_pi))

  (setq e_n (fix (/ en_pi 2)))
  (setq f_m (fix (/ fn_pi 2)))
  (setq ss2 (entnext ss1) e_step (+ g_pi e_pi e_pi h_pi))
  (setq ss3 (entnext ss2) f_step (+ i_pi f_pi f_pi j_pi))
  (setq ss4 (entnext ss3) g_n e_n i_m f_m)
  (if (> en_pi (* e_n 2)) (setq g_n (+ e_n 1)))
  (if (> fn_pi (* f_m 2)) (setq i_m (+ f_m 1)))
  (cond ((and (> e_n 1) (> f_m 1))
         (command "array" ss1 "" "r" g_n i_m e_step f_step)
         (command "array" ss2 "" "r" e_n i_m e_step f_step)
         (command "array" ss3 "" "r" g_n f_m e_step f_step)
         (command "array" ss4 "" "r" e_n f_m e_step f_step)
        )
	((and (= e_n 1) (> f_m 1))
         (command "array" ss1 "" "r" g_n i_m e_step f_step)
         (command "array" ss2 "" "r" 1 i_m f_step)
         (command "array" ss3 "" "r" g_n f_m e_step f_step)
         (command "array" ss4 "" "r" 1 f_m f_step)
	)
	((and (> e_n 1) (= f_m 1))
         (command "array" ss1 "" "r" g_n i_m e_step f_step)
         (command "array" ss2 "" "r" e_n i_m e_step f_step)
         (command "array" ss3 "" "r" g_n 1 e_step)
         (command "array" ss4 "" "r" e_n 1 e_step)
        )
	((and (= e_n 1) (= f_m 1))
         (command "array" ss1 "" "r" g_n i_m e_step f_step)
         (command "array" ss2 "" "r" 1 i_m f_step)
         (command "array" ss3 "" "r" g_n f_m e_step)
         (command "array" ss4 "" "r" 1 1)
        )
  )
)


;main program

(chang)
(setvar "OSMODE" 2)
