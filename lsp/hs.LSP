(defun zero ()
  (command "pline"
	   (list 0.135159 2.5)
	   "w"
	   0
	   0
	   (list 0.820522 2.5)
	   (list 1.36754 1.5)
	   (list 1.36754 1.0)
	   (list 1.36754 -1.5)
	   (list 0.820522 -2.5)
	   (list -0.820522 -2.5)
	   (list -1.36754 -1.5)
	   (list -1.36754 1.5)
	   (list -0.820522 2.5)
	   (list 0.135104 2.5)
	   (list 0.135104 1.5)
	   (list -0.547014 1.5)
	   (list -0.820522 1.0)
	   (list -0.820522 -1.0)
	   (list -0.547014 -1.5)
	   (list 0.547014 -1.5)
	   (list 0.820522 -1.0)
	   (list 0.820522 1.0)
	   (list 0.547014 1.5)
	   (list 0.135159 1.5)
	   "c"
  )
)
(defun one ()
  (command "pline"
	   (list -0.25923 2.5)
	   "w"
	   0
	   0
	   (list 0.79077 2.5)
	   (list 0.79077 -2.0)
	   (list 1.31577 -2.0)
	   (list 1.31577 -2.5)
	   (list -0.78423 -2.5)
	   (list -0.78423 -2.0)
	   (list -0.25923 -2.0)
	   (list -0.25923 1.5)
	   (list -0.78423 1.0)
	   (list -1.30923 1.5)
	   "c"
  )
)
(defun two ()
  (command "pline"
	   (list -1.36575 1.0)
	   "w"
	   0
	   0
	   (list -1.36575 1.5)
	   (list -0.56575 2.5)
	   (list 0.56575 2.5)
	   (list 1.36575 1.5)
	   (list 1.36575 0.5)
	   (list 0.56575 -0.5)
	   (list 0.23425 -0.5)
	   (list -0.56575 -1.5)
	   (list 1.36575 -1.5)
	   (list 1.36575 -2.5)
	   (list -1.36575 -2.5)
	   (list -1.36575 -1.0)
	   (list -0.16575 0.5)
	   (list 0.3471 0.5)
	   (list 0.7471 1.0)
	   (list 0.3471 1.5)
	   (list -0.16575 1.5)
	   (list -0.56575 1.0)
	   "c"
  )
)
(defun three ()
  (command "pline"
	   (list 1.3662 -0.5)
	   "w"
	   0
	   0
	   (list 1.3662 -1.5)
	   (list 0.81972 -2.5)
	   (list -0.81972 -2.5)
	   (list -1.3662 -1.5)
	   (list -1.3662 -0.5)
	   (list -0.81972 -0.5)
	   (list -0.81972 -1.0)
	   (list -0.54648 -1.5)
	   (list 0.54648 -1.5)
	   (list 0.81972 -1.0)
	   (list 0.54648 -0.5)
	   (list 0.0 -0.5)
	   (list 0.0 0.5)
	   (list 0.54648 0.5)
	   (list 0.81972 1.0)
	   (list 0.54648 1.5)
	   (list -0.54648 1.5)
	   (list -0.81972 1.0)
	   (list -0.81972 0.5)
	   (list -1.3662 0.5)
	   (list -1.3662 1.5)
	   (list -0.81972 2.5)
	   (list 0.81972 2.5)
	   (list 1.3662 1.5)
	   (list 1.3662 0.5)
	   (list 1.09296 0.0)
	   "c"
  )
)
(defun four ()
  (command "pline"
	   (list -0.284637 -0.5)
	   "w"
	   0
	   0
	   (list 0.276123 -0.5)
	   (list 0.276123 1.5)
	   (list -0.828368 -0.5)
	   (list -0.284706 -0.5)
	   (list -0.284706 -1.5)
	   (list -1.38061 -1.5)
	   (list -1.38061 -0.5)
	   (list 0.276123 2.5)
	   (list 0.828368 2.5)
	   (list 0.828368 -0.5)
	   (list 1.38061 -0.5)
	   (list 1.38061 -1.5)
	   (list 0.828368 -1.5)
	   (list 0.828368 -2.5)
	   (list 0.276123 -2.5)
	   (list 0.276123 -1.5)
	   (list -0.284637 -1.5)
	   "c"
  )
)
(defun five ()
  (command "pline"
	   (list 0.786811 -2.5)
	   "w"
	   0
	   0
	   (list 1.43091 -1.5)
	   (list 1.43091 -0.5)
	   (list 0.786811 0.5)
	   (list -0.786811 0.5)
	   (list -0.786811 1.5)
	   (list 1.43091 1.5)
	   (list 1.43091 2.5)
	   (list -1.43091 2.5)
	   (list -1.43091 -0.5)
	   (list 0.464761 -0.5)
	   (list 0.786811 -1.0)
	   (list 0.464761 -1.5)
	   (list -0.464761 -1.5)
	   (list -0.786811 -1.0)
	   (list -1.43091 -1.0)
	   (list -1.43091 -1.5)
	   (list -0.786811 -2.5)
	   "c"
  )
)
(defun six ()
  (command "pline"
	   (list 0.083883 -1.5)
	   "w"
	   0
	   0
	   (list 0.550654 -1.5)
	   (list 0.82598 -1.0)
	   (list 0.550654 -0.5)
	   (list -0.82598 -0.5)
	   (list -0.82598 -1.0)
	   (list -0.550654 -1.5)
	   (list 0.0838124 -1.5)
	   (list 0.0838124 -2.5)
	   (list -0.82598 -2.5)
	   (list -1.37663 -1.5)
	   (list -1.37663 1.5)
	   (list -0.82598 2.5)
	   (list 0.82598 2.5)
	   (list 1.37663 1.5)
	   (list 1.37663 1.0)
	   (list 0.82598 1.0)
	   (list 0.550654 1.5)
	   (list -0.550654 1.5)
	   (list -0.82598 1.0)
	   (list -0.82598 0.5)
	   (list 0.82598 0.5)
	   (list 1.37663 -0.5)
	   (list 1.37663 -1.0)
	   (list 1.37663 -1.5)
	   (list 0.82598 -2.5)
	   (list 0.083883 -2.5)
	   "c"
  )
)
(defun seven ()
  (command "pline"
	   (list -1.34316 -2.0)
	   "w"
	   0
	   0
	   (list -1.34316 -2.5)
	   (list -0.805896 -2.5)
	   (list 1.34316 1.5)
	   (list 1.34316 2.5)
	   (list -1.34316 2.5)
	   (list -1.34316 1.5)
	   (list 0.537264 1.5)
	   "c"
  )
)
(defun eight ()
  (command "pline"
	   (list -0.0107966 1.5)
	   "w"
	   0
	   0
	   (list 0.378389 1.5)
	   (list 0.772211 1.0)
	   (list 0.378389 0.5)
	   (list -0.518801 0.5)
	   (list -0.912623 1.0)
	   (list -0.518801 1.5)
	   (list -0.0108754 1.5)
	   (list -0.0108754 2.5)
	   (list -0.586125 2.5)
	   (list -1.37377 1.5)
	   (list -1.37377 0.5)
	   (list -0.979947 0.0)
	   (list -1.37377 -0.5)
	   (list -1.37377 -1.5)
	   (list -0.586125 -2.5)
	   (list 0.00789834 -2.5)
	   (list 0.00789834 -1.5)
	   (list -0.518801 -1.5)
	   (list -0.912623 -1.0)
	   (list -0.518801 -0.5)
	   (list 0.378389 -0.5)
	   (list 0.772211 -1.0)
	   (list 0.378389 -1.5)
	   (list 0.0079771 -1.5)
	   (list 0.0079771 -2.5)
	   (list 0.586125 -2.5)
	   (list 1.37377 -1.5)
	   (list 1.37377 -1.0)
	   (list 1.37377 -0.5)
	   (list 0.979947 0.0)
	   (list 1.37377 0.5)
	   (list 1.37377 1.0)
	   (list 1.37377 1.5)
	   (list 0.586125 2.5)
	   (list -0.0107966 2.5)
	   "c"
  )
)
(defun nine ()
  (command "pline"
	   (list 0.155404 2.5)
	   "w"
	   0
	   0
	   (list 0.823397 2.5)
	   (list 1.37233 1.5)
	   (list 1.37233 0.5)
	   (list 1.37233 -1.5)
	   (list 0.823397 -2.5)
	   (list -0.823397 -2.5)
	   (list -1.37233 -1.5)
	   (list -1.37233 -1.0)
	   (list -0.823397 -1.0)
	   (list -0.548931 -1.5)
	   (list 0.548931 -1.5)
	   (list 0.823397 -1.0)
	   (list 0.823397 -0.5)
	   (list -0.823397 -0.5)
	   (list -1.37233 0.5)
	   (list -1.37233 1.5)
	   (list -0.823397 2.5)
	   (list 0.155337 2.5)
	   (list 0.155337 1.5)
	   (list -0.548931 1.5)
	   (list -0.823397 1.0)
	   (list -0.548931 0.5)
	   (list 0.823397 0.5)
	   (list 0.823397 1.0)
	   (list 0.548931 1.5)
	   (list 0.155404 1.5)
	   "c"
  )
)
(defun scale (layer_name ke kf)
  (setq
    ss_lwpl (ssget "x"
		   (list (cons 0 "lwpolyline") (cons 8 layer_name))
	    )
  )
  (if ss_lwpl
    (progn
      (setq ss_cnt (sslength ss_lwpl))
      (setq i_loop 0)
      (while (< i_loop ss_cnt)
	(setq pl_dt (entget (ssname ss_lwpl i_loop)))
	(setq dt nil)
	(while pl_dt
	  (if (/= (caar pl_dt) 10)
	    (setq dt (append dt (list (car pl_dt))))
	    (progn
	      (setq scl_x (* (cadar pl_dt) scal))
	      (setq scl_y (* (caddar pl_dt) ke))
	      (setq
		dt (append dt (list (cons 10 (list scl_x scl_y 0))))
	      )
	    )
	  )
	  (setq pl_dt (cdr pl_dt))
	)
	(entmod dt)
	(setq i_loop (1+ i_loop))
      )
    )
  )
)
(defun c:hs (/	     c_date  dt_id   str_new id_len  ke	     m
	     ss	     dep_x   pt1_y   pt1_x   pt1     pt2     pt2_x
	     pt2_y   x_dis   y_dis   scal1   scal
	    )
  (setvar "osmode" 512)
  (princ
    "\n****请选取所加文字最大范围的两对角点---左下和右上****"
  )
  (setq pt1 (getpoint "\n请点取左下角:"))
  (setq pt2 (getpoint "\n请点取右上角:"))
  (setvar "osmode" 0)
  (setq pt1_x (car pt1))
  (setq pt2_x (car pt2))
  (setq pt1_y (cadr pt1))
  (setq pt2_y (cadr pt2))
  (setq x_dis (abs (- pt1_x pt2_x)))
  (setq y_dis (abs (- pt1_y pt2_y)))
  (setq scal1 (/ y_dis 6))
  (setq scal (/ scal1 3))
  (setq ke (/ x_dis 5))
  (setq c_date (getvar "cdate"))
  (setq dt_id (itoa (fix c_date)))
  (setq str_new (strcat (substr dt_id 5 4) (substr dt_id 3 2)))
  (setq id_len (strlen str_new))
  (while (not (tblsearch "layer" "tem"))
    (command "layer" "n" "tem" "")
  )
  (command "layer" "m" "tem" "")
  (setq m 1)
  (while (<= m id_len)
    (setq id_c (substr str_new m 1))
    (if	(equal id_c "0")
      (zero)
    )
    (if	(equal id_c "1")
      (one)
    )
    (if	(equal id_c "2")
      (two)
    )
    (if	(equal id_c "3")
      (three)
    )
    (if	(equal id_c "4")
      (four)
    )
    (if	(equal id_c "5")
      (five)
    )
    (if	(equal id_c "6")
      (six)
    )
    (if	(equal id_c "7")
      (seven)
    )
    (if	(equal id_c "8")
      (eight)
    )
    (if	(equal id_c "9")
      (nine)
    )
    (command "zoom" "e" "")
    (setq ss (ssget "x" (list (cons 0 "lwpolyline") (cons 8 "tem"))))
    (command "change" ss "" "p" "la" "tem" "")
    (scale "tem" ke scal)
    (command "change" ss "" "p" "la" "0" "")
    (command "rotate" ss "" "0,0" 90)
    (setq dep_y (+ (- pt1_y (* scal1 0.5)) (* m scal1)))
    (command "move"
	     ss
	     ""
	     "0,0"
	     (list (+ pt1_x (* ke 2.5)) dep_y)
	     ""
    )
    (setq m (+ m 1))
  )
  (command "layer" "m" "0" "")
  (command "purge" "la" "" "n")
)
(prompt"\n----敲HS运行程序----")
