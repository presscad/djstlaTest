(defun c:hth()
  (setq	layer_name
	 (strcase (getstring "请键入层名:"))
  )
  (while (and (not (setq found (tblsearch "LAYER" layer_name)))
	      (/= layer_name "")
	 )
    (setq layer_name (getstring "请键入层名:"))
  )
  (command "layer" "M" layer_name "")
  (setvar "CEcolor" "white")
  (setq ss_pl (ssget "x" (list (cons 0 "hatch")(cons 8 layer_name))))
  (command "erase" ss_pl "")
  (setq hth_scl (getreal "请输入比例:"))
  (setq ss_pl (ssget "x" (list (cons 0 "lwpolyline")(cons 8 layer_name))))
  (if ss_pl
    (progn
      (setq all_cnt (sslength ss_pl) )
      (setq cnt 0)      
      (while (< cnt all_cnt)
	(setq ent_name (ssname ss_pl cnt))
	(command "hatch" "ansi31" hth_scl "" ent_name "")
	(setq cnt (+ cnt 1))
	)
      )
    )
  (setq ss_pl (ssget "x" (list (cons 0 "circle")(cons 8 layer_name))))
  (if ss_pl
    (progn
      (setq all_cnt (sslength ss_pl) )
      (setq cnt 0)      
      (while (< cnt all_cnt)
	(setq ent_name (ssname ss_pl cnt))
	(command "hatch" "ansi31" hth_scl "" ent_name "")
	(setq cnt (+ cnt 1))
	)
      )
    )
   (setvar "CEcolor" "bylayer")
  )
