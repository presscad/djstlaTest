;专门用于cl04_pellicle制作.
(defun draw_6i2f () ;6inch/2fields.
        (command "pline" (list 139.9 99.506) "w" 0 0 
                         (list 140.9 99.506) 
                         (list 140.9 99.514) 
                         (list 139.9 99.514) 
                         "c"
         )
        (command "pline" (list 140.396 97.41) "w" 0 0 
                         (list 140.404 97.41) 
                         (list 140.404 100.01) 
                         (list 140.396 100.01) 
                         "c"
         )
        (command "pline" (list 11.5 99.506) "w" 0 0 
                         (list 12.5 99.506) 
                         (list 12.5 99.514) 
                         (list 11.5 99.514) 
                         "c"
         )
        (command "pline" (list 11.996 97.41) "w" 0 0 
                         (list 12.004 97.41) 
                         (list 12.004 100.01) 
                         (list 11.996 100.01) 
                         "c"
         )
        (command "pline" (list 12.996 22.52) "w" 0 0 
                         (list 13.004 22.52) 
                         (list 13.004 22.72) 
                         (list 12.996 22.72) 
                         "c"
         )
        (command "pline" (list 12.5 22.616) "w" 0 0 
                         (list 13.5 22.616) 
                         (list 13.5 22.624) 
                         (list 12.5 22.624) 
                         "c"
         )
        (command "pline" (list 76.196 22.52) "w" 0 0 
                         (list 76.204 22.52) 
                         (list 76.204 22.72) 
                         (list 76.196 22.72) 
                         "c"
         )
        (command "pline" (list 75.7 22.616) "w" 0 0 
                         (list 76.7 22.616) 
                         (list 76.7 22.624) 
                         (list 75.7 22.624) 
                         "c"
         )
        (command "pline" (list 139.396 22.52) "w" 0 0 
                         (list 139.404 22.52) 
                         (list 139.404 22.72) 
                         (list 139.396 22.72) 
                         "c"
         )
        (command "pline" (list 138.9 22.616) "w" 0 0 
                         (list 139.9 22.616) 
                         (list 139.9 22.624) 
                         (list 138.9 22.624) 
                         "c"
         )
        (command "pline" (list 12.996 61.63) "w" 0 0 
                         (list 13.004 61.63) 
                         (list 13.004 61.83) 
                         (list 12.996 61.83) 
                         "c"
         )
        (command "pline" (list 12.5 61.726) "w" 0 0 
                         (list 13.5 61.726) 
                         (list 13.5 61.734) 
                         (list 12.5 61.734) 
                         "c"
         )
        (command "pline" (list 76.196 61.63) "w" 0 0 
                         (list 76.204 61.63) 
                         (list 76.204 61.83) 
                         (list 76.196 61.83) 
                         "c"
         )
        (command "pline" (list 75.7 61.726) "w" 0 0 
                         (list 76.7 61.726) 
                         (list 76.7 61.734) 
                         (list 75.7 61.734) 
                         "c"
         )
        (command "pline" (list 139.396 61.63) "w" 0 0 
                         (list 139.404 61.63) 
                         (list 139.404 61.83) 
                         (list 139.396 61.83) 
                         "c"
         )
        (command "pline" (list 138.9 61.726) "w" 0 0 
                         (list 139.9 61.726) 
                         (list 139.9 61.734) 
                         (list 138.9 61.734) 
                         "c"
         )
        (command "pline" (list 12.996 67.63) "w" 0 0 
                         (list 13.004 67.63) 
                         (list 13.004 67.83) 
                         (list 12.996 67.83) 
                         "c"
         )
        (command "pline" (list 12.5 67.726) "w" 0 0 
                         (list 13.5 67.726) 
                         (list 13.5 67.734) 
                         (list 12.5 67.734) 
                         "c"
         )
        (command "pline" (list 76.196 67.63) "w" 0 0 
                         (list 76.204 67.63) 
                         (list 76.204 67.83) 
                         (list 76.196 67.83) 
                         "c"
         )
        (command "pline" (list 75.7 67.726) "w" 0 0 
                         (list 76.7 67.726) 
                         (list 76.7 67.734) 
                         (list 75.7 67.734) 
                         "c"
         )
        (command "pline" (list 139.396 67.63) "w" 0 0 
                         (list 139.404 67.63) 
                         (list 139.404 67.83) 
                         (list 139.396 67.83) 
                         "c"
         )
        (command "pline" (list 138.9 67.726) "w" 0 0 
                         (list 139.9 67.726) 
                         (list 139.9 67.734) 
                         (list 138.9 67.734) 
                         "c"
         )
        (command "pline" (list 12.996 106.74) "w" 0 0 
                         (list 13.004 106.74) 
                         (list 13.004 106.94) 
                         (list 12.996 106.94) 
                         "c"
         )
        (command "pline" (list 12.5 106.836) "w" 0 0 
                         (list 13.5 106.836) 
                         (list 13.5 106.844) 
                         (list 12.5 106.844) 
                         "c"
         )
        (command "pline" (list 76.196 106.74) "w" 0 0 
                         (list 76.204 106.74) 
                         (list 76.204 106.94) 
                         (list 76.196 106.94) 
                         "c"
         )
        (command "pline" (list 75.7 106.836) "w" 0 0 
                         (list 76.7 106.836) 
                         (list 76.7 106.844) 
                         (list 75.7 106.844) 
                         "c"
         )
        (command "pline" (list 139.396 106.74) "w" 0 0 
                         (list 139.404 106.74) 
                         (list 139.404 106.94) 
                         (list 139.396 106.94) 
                         "c"
         )
        (command "pline" (list 138.9 106.836) "w" 0 0 
                         (list 139.9 106.836) 
                         (list 139.9 106.844) 
                         (list 138.9 106.844) 
                         "c"
         )
        (command "pline" (list 4.95 99.4) "w" 0 0 
                         (list 6.45 99.4) 
                         (list 6.45 100.9) 
                         (list 4.95 100.9) 
                         "c"
         )
        (command "pline" (list 17.25 107.4) "w" 0 0 
                         (list 18.75 107.4) 
                         (list 18.75 108.9) 
                         (list 17.25 108.9) 
                         "c"
         )
        (command "pline" (list 133.65 65.668) "w" 0 0 
                         (list 135.15 65.668) 
                         (list 135.15 67.168) 
                         (list 133.65 67.168) 
                         "c"
         )
        (command "pline" (list 145.95 73.67) "w" 0 0 
                         (list 147.45 73.67) 
                         (list 147.45 75.17) 
                         (list 145.95 75.17) 
                         "c"
         )
        (command "pline" (list 127.049 11.2722) "w" 0 0 
                         (list 127.56 11.2747) 
                         (list 127.562 11.226) 
                         (list 127.424 11.2156) 
                         (list 127.349 11.2077) 
                         (list 126.995 10.9664) 
                         (list 127.524 10.4577) 
                         (list 127.57 10.4477) 
                         (list 127.709 10.4477) 
                         (list 127.717 10.3989) 
                         (list 126.984 10.391) 
                         (list 126.979 10.4502) 
                         (list 127.108 10.4527) 
                         (list 126.72 10.8202) 
                         (list 126.717 10.8098) 
                         (list 126.709 10.7993) 
                         (list 126.717 10.4577) 
                         (list 126.732 10.4423) 
                         (list 126.879 10.4423) 
                         (list 126.884 10.4039) 
                         (list 126.871 10.3935) 
                         (list 126.195 10.3885) 
                         (list 126.19 10.4064) 
                         (list 126.19 10.4373) 
                         (list 126.213 10.4423) 
                         (list 126.352 10.4502) 
                         (list 126.344 11.2052) 
                         (list 126.226 11.2077) 
                         (list 126.19 11.2106) 
                         (list 126.185 11.2568) 
                         (list 126.219 11.2643) 
                         (list 126.874 11.2693) 
                         (list 126.874 11.2231) 
                         (list 126.864 11.2106) 
                         (list 126.72 11.2077) 
                         (list 126.709 11.1848) 
                         (list 126.709 10.8739) 
                         (list 126.722 10.8635) 
                         (list 127.21 11.1952) 
                         (list 127.2 11.2181) 
                         (list 127.074 11.2131) 
                         (list 127.041 11.2206) 
                         (list 127.041 11.2618) 
                         "c"
         )
        (command "pline" (list 125.278 10.6402) "w" 0 0 
                         (list 125.263 10.6148) 
                         (list 125.265 10.391) 
                         (list 125.291 10.3756) 
                         (list 125.368 10.3756) 
                         (list 125.399 10.3964) 
                         (list 125.445 10.4193) 
                         (list 125.481 10.4014) 
                         (list 125.561 10.381) 
                         (list 125.656 10.3656) 
                         (list 125.769 10.3627) 
                         (list 125.885 10.3656) 
                         (list 125.972 10.3835) 
                         (list 126.08 10.4323) 
                         (list 126.162 10.4989) 
                         (list 126.195 10.5323) 
                         (list 126.216 10.5889) 
                         (list 126.229 10.6581) 
                         (list 126.226 10.7352) 
                         (list 126.193 10.7993) 
                         (list 126.172 10.8381) 
                         (list 126.131 10.8664) 
                         (list 126.075 10.8973) 
                         (list 126.0 10.9227) 
                         (list 125.92 10.946) 
                         (list 125.843 10.9639) 
                         (list 125.779 10.9739) 
                         (list 125.71 10.9868) 
                         (list 125.653 10.9998) 
                         (list 125.581 11.0102) 
                         (list 125.532 11.0281) 
                         (list 125.481 11.0385) 
                         (list 125.458 11.051) 
                         (list 125.44 11.0743) 
                         (list 125.44 11.1002) 
                         (list 125.443 11.1206) 
                         (list 125.453 11.1464) 
                         (list 125.484 11.1693) 
                         (list 125.525 11.1898) 
                         (list 125.558 11.2002) 
                         (list 125.592 11.2052) 
                         (list 125.63 11.2181) 
                         (list 125.692 11.2181) 
                         (list 125.753 11.2181) 
                         (list 125.828 11.2077) 
                         (list 125.89 11.1823) 
                         (list 125.941 11.1643) 
                         (list 125.985 11.1077) 
                         (list 126.018 11.0589) 
                         (list 126.041 11.0281) 
                         (list 126.064 11.0177) 
                         (list 126.118 11.0177) 
                         (list 126.124 11.0331) 
                         (list 126.124 11.2539) 
                         (list 126.103 11.2643) 
                         (list 126.036 11.2593) 
                         (list 126.016 11.236) 
                         (list 125.992 11.2285) 
                         (list 125.974 11.2285) 
                         (list 125.949 11.2285) 
                         (list 125.915 11.2439) 
                         (list 125.833 11.2668) 
                         (list 125.751 11.2747) 
                         (list 125.679 11.2772) 
                         (list 125.61 11.2747) 
                         (list 125.535 11.2618) 
                         (list 125.463 11.231) 
                         (list 125.401 11.2052) 
                         (list 125.368 11.1718) 
                         (list 125.324 11.131) 
                         (list 125.294 11.0818) 
                         (list 125.27 11.0102) 
                         (list 125.278 10.9485) 
                         (list 125.294 10.8818) 
                         (list 125.329 10.8431) 
                         (list 125.365 10.8202) 
                         (list 125.435 10.7868) 
                         (list 125.532 10.7531) 
                         (list 125.615 10.7327) 
                         (list 125.682 10.7252) 
                         (list 125.738 10.7223) 
                         (list 125.807 10.7123) 
                         (list 125.879 10.6993) 
                         (list 125.956 10.6789) 
                         (list 126.003 10.6506) 
                         (list 126.036 10.6148) 
                         (list 126.054 10.581) 
                         (list 126.052 10.5298) 
                         (list 126.016 10.4785) 
                         (list 125.972 10.4577) 
                         (list 125.923 10.4323) 
                         (list 125.877 10.4218) 
                         (list 125.828 10.4193) 
                         (list 125.769 10.4118) 
                         (list 125.702 10.4143) 
                         (list 125.646 10.4243) 
                         (list 125.556 10.4423) 
                         (list 125.504 10.476) 
                         (list 125.455 10.5093) 
                         (list 125.412 10.5531) 
                         (list 125.376 10.6018) 
                         (list 125.36 10.6298) 
                         "c"
         )
        (command "pline" (list 123.635 10.3756) "w" 0 0 
                         (list 124.057 10.3781) 
                         (list 124.709 10.9098) 
                         (list 124.555 10.4606) 
                         (list 124.499 10.3835) 
                         (list 124.889 10.3756) 
                         (list 125.169 11.2822) 
                         (list 124.774 11.2772) 
                         (list 123.687 10.4089) 
                         (list 123.635 10.3885) 
                         "c"
         )
        (command "pline" (list 116.925 11.2206) "w" 0 0 
                         (list 116.969 11.2285) 
                         (list 117.588 11.231) 
                         (list 117.617 11.2131) 
                         (list 117.614 11.1743) 
                         (list 117.604 11.1693) 
                         (list 117.434 11.1693) 
                         (list 117.434 10.6248) 
                         (list 117.439 10.5914) 
                         (list 117.447 10.5348) 
                         (list 117.462 10.5039) 
                         (list 117.478 10.4552) 
                         (list 117.522 10.4193) 
                         (list 117.583 10.4014) 
                         (list 117.632 10.3989) 
                         (list 117.714 10.3935) 
                         (list 117.778 10.3989) 
                         (list 117.848 10.4064) 
                         (list 117.899 10.4193) 
                         (list 117.956 10.4398) 
                         (list 117.999 10.4835) 
                         (list 118.025 10.5377) 
                         (list 118.03 10.5631) 
                         (list 118.033 10.6327) 
                         (list 118.03 10.7764) 
                         (list 118.03 11.1335) 
                         (list 118.025 11.1564) 
                         (list 118.01 11.1668) 
                         (list 118.002 11.1718) 
                         (list 117.892 11.1668) 
                         (list 117.863 11.1798) 
                         (list 117.863 11.226) 
                         (list 117.884 11.2285) 
                         (list 118.218 11.2335) 
                         (list 118.226 11.2106) 
                         (list 118.226 11.1823) 
                         (list 118.187 11.1693) 
                         (list 118.149 11.1643) 
                         (list 118.136 11.1435) 
                         (list 118.131 11.1231) 
                         (list 118.128 11.0973) 
                         (list 118.136 10.576) 
                         (list 118.128 10.5273) 
                         (list 118.113 10.4964) 
                         (list 118.089 10.4577) 
                         (list 118.064 10.4273) 
                         (list 118.028 10.4064) 
                         (list 117.958 10.3781) 
                         (list 117.899 10.3577) 
                         (list 117.843 10.3448) 
                         (list 117.82 10.3398) 
                         (list 117.491 10.3318) 
                         (list 117.46 10.3373) 
                         (list 117.385 10.3473) 
                         (list 117.319 10.3602) 
                         (list 117.236 10.3835) 
                         (list 117.195 10.4064) 
                         (list 117.164 10.4168) 
                         (list 117.141 10.4398) 
                         (list 117.126 10.4681) 
                         (list 117.108 10.5014) 
                         (list 117.095 10.5502) 
                         (list 117.087 10.6223) 
                         (list 117.087 10.7018) 
                         (list 117.087 11.1435) 
                         (list 117.08 11.1668) 
                         (list 117.067 11.1693) 
                         (list 116.925 11.1668) 
                         (list 116.92 11.1873) 
                         "c"
         )
        (command "pline" (list 114.653 10.2327) "w" 0 0 
                         (list 116.812 11.1706) 
                         (list 116.825 11.1514) 
                         (list 116.812 11.1381) 
                         (list 116.231 10.8914) 
                         (list 116.228 10.8656) 
                         (list 115.494 10.5668) 
                         (list 115.481 10.5348) 
                         (list 114.689 10.2035) 
                         "c"
         )
        (command "pline" (list 114.78 10.1223) "w" 0 0 
                         (list 114.741 10.1548) 
                         (list 114.734 10.1614) 
                         (list 116.79 11.0443) 
                         (list 116.816 11.0443) 
                         (list 116.825 11.0248) 
                         (list 116.316 10.8106) 
                         (list 116.238 10.7843) 
                         (list 116.238 10.7552) 
                         (list 115.491 10.4535) 
                         (list 115.491 10.4273) 
                         "c"
         )
        (command "pline" (list 114.845 10.0898) "w" 0 0 
                         (list 116.761 10.9143) 
                         (list 116.783 10.9177) 
                         (list 116.796 10.9077) 
                         (list 116.238 10.6643) 
                         (list 116.241 10.6448) 
                         (list 115.507 10.3431) 
                         (list 115.51 10.3139) 
                         (list 114.968 10.0835) 
                         (list 114.981 10.0706) 
                         (list 114.91 10.0606) 
                         (list 114.88 10.0639) 
                         "c"
         )
        (command "pline" (list 114.952 10.0252) "w" 0 0 
                         (list 116.748 10.7877) 
                         (list 116.757 10.7843) 
                         (list 116.767 10.7748) 
                         (list 116.761 10.7585) 
                         (list 116.257 10.5506) 
                         (list 116.251 10.5377) 
                         (list 115.51 10.2264) 
                         (list 115.514 10.2068) 
                         (list 115.283 10.0998) 
                         (list 115.231 10.0898) 
                         (list 115.221 10.0802) 
                         (list 115.251 10.0735) 
                         (list 115.238 10.0606) 
                         (list 115.195 10.0639) 
                         (list 115.189 10.0639) 
                         (list 115.075 10.0089) 
                         (list 115.004 9.99269) 
                         (list 114.958 10.0219) 
                         "c"
         )
        (command "pline" (list 115.098 9.96644) "w" 0 0 
                         (list 116.689 10.6385) 
                         (list 116.696 10.6256) 
                         (list 116.702 10.6127) 
                         (list 116.247 10.4273) 
                         (list 116.241 10.4143) 
                         (list 115.751 10.2068) 
                         (list 115.507 10.106) 
                         (list 115.504 10.0931) 
                         (list 115.504 10.0769) 
                         (list 115.514 10.0639) 
                         (list 115.449 10.0573) 
                         (list 115.202 9.9406) 
                         (list 115.156 9.93102) 
                         (list 115.137 9.93727) 
                         "c"
         )
        (command "pline" (list 115.247 9.91477) "w" 0 0 
                         (list 116.556 10.4731) 
                         (list 116.566 10.4827) 
                         (list 116.598 10.4889) 
                         (list 116.595 10.4698) 
                         (list 116.585 10.4502) 
                         (list 116.27 10.3202) 
                         (list 116.26 10.2848) 
                         (list 115.764 10.0802) 
                         (list 115.754 10.0769) 
                         (list 115.78 10.0639) 
                         (list 115.702 10.0639) 
                         (list 115.556 10.0056) 
                         (list 115.53 10.0023) 
                         (list 115.52 9.97935) 
                         (list 115.517 9.95685) 
                         (list 115.38 9.89852) 
                         (list 115.319 9.89852) 
                         "c"
         )
        (command "pline" (list 115.497 9.89519) "w" 0 0 
                         (list 115.527 9.91769) 
                         (list 116.442 10.3073) 
                         (list 116.452 10.2943) 
                         (list 116.439 10.2781) 
                         (list 116.329 10.2327) 
                         (list 116.27 10.2068) 
                         (list 116.267 10.1806) 
                         (list 116.046 10.0931) 
                         (list 116.023 10.0964) 
                         (list 116.027 10.0802) 
                         (list 116.053 10.0706) 
                         (list 115.981 10.0639) 
                         (list 115.575 9.89186) 
                         "c"
         )
        (command "pline" (list 115.332 10.6102) "w" 0 0 
                         (list 117.52 11.5352) 
                         (list 117.485 11.5677) 
                         (list 117.449 11.5839) 
                         (list 116.64 11.2335) 
                         (list 116.663 11.2172) 
                         (list 115.936 10.9056) 
                         (list 115.897 10.8764) 
                         (list 115.316 10.6231) 
                         "c"
         )
        (command "pline" (list 115.322 10.7302) "w" 0 0 
                         (list 115.364 10.7273) 
                         (list 117.413 11.6197) 
                         (list 117.381 11.6422) 
                         (list 117.329 11.6456) 
                         (list 116.644 11.3535) 
                         (list 116.66 11.3277) 
                         (list 115.91 11.0227) 
                         (list 115.894 11.0031) 
                         (list 115.855 10.9802) 
                         (list 115.325 10.7498) 
                         "c"
         )
        (command "pline" (list 115.354 10.8568) "w" 0 0 
                         (list 117.313 11.691) 
                         (list 117.283 11.7202) 
                         (list 117.235 11.7235) 
                         (list 117.209 11.7172) 
                         (list 116.679 11.4802) 
                         (list 116.653 11.4639) 
                         (list 116.64 11.4347) 
                         (list 115.91 11.1327) 
                         (list 115.9 11.1135) 
                         (list 115.341 10.8764) 
                         "c"
         )
        (command "pline" (list 115.384 10.9964) "w" 0 0 
                         (list 115.426 10.9964) 
                         (list 115.475 11.0093) 
                         (list 117.196 11.7656) 
                         (list 117.144 11.7818) 
                         (list 117.095 11.7818) 
                         (list 116.634 11.5839) 
                         (list 116.634 11.5581) 
                         (list 115.894 11.2497) 
                         (list 115.881 11.2335) 
                         (list 115.842 11.2106) 
                         (list 115.374 11.0064) 
                         "c"
         )
        (command "pline" (list 115.449 11.1427) "w" 0 0 
                         (list 115.504 11.1556) 
                         (list 117.066 11.821) 
                         (list 117.014 11.8372) 
                         (list 116.952 11.8435) 
                         (list 116.936 11.8406) 
                         (list 116.644 11.7106) 
                         (list 116.624 11.6652) 
                         (list 115.89 11.3631) 
                         (list 115.816 11.3177) 
                         (list 115.458 11.1652) 
                         (list 115.442 11.1489) 
                         "c"
         )
        (command "pline" (list 115.553 11.3047) "w" 0 0 
                         (list 115.579 11.3014) 
                         (list 116.89 11.8597) 
                         (list 116.832 11.876) 
                         (list 116.757 11.8727) 
                         (list 116.618 11.8081) 
                         (list 116.627 11.7947) 
                         (list 115.894 11.4897) 
                         (list 115.89 11.4639) 
                         (list 115.553 11.3177) 
                         "c"
         )
        (command "pline" (list 115.721 11.4997) "w" 0 0 
                         (list 115.734 11.4897) 
                         (list 115.78 11.506) 
                         (list 116.676 11.8827) 
                         (list 116.634 11.8922) 
                         (list 116.588 11.8922) 
                         (list 115.868 11.5906) 
                         (list 115.864 11.5677) 
                         (list 115.715 11.506) 
                         "c"
         )
        (command "pline" (list 122.8 10.4273) "w" 0 0 
                         (list 122.779 10.4218) 
                         (list 122.782 10.381) 
                         (list 122.807 10.3756) 
                         (list 123.46 10.3756) 
                         (list 123.478 10.386) 
                         (list 123.478 10.4273) 
                         (list 123.445 10.4323) 
                         (list 123.298 10.4323) 
                         (list 123.291 11.1923) 
                         (list 123.442 11.1898) 
                         (list 123.468 11.2052) 
                         (list 123.47 11.2385) 
                         (list 123.46 11.2489) 
                         (list 123.437 11.2539) 
                         (list 122.908 11.2514) 
                         (list 122.674 10.7764) 
                         (list 122.664 10.7685) 
                         (list 122.422 11.2489) 
                         (list 121.844 11.2464) 
                         (list 121.839 11.1977) 
                         (list 121.862 11.1873) 
                         (list 122.016 11.1873) 
                         (list 122.019 10.4785) 
                         (list 122.013 10.4552) 
                         (list 122.001 10.4298) 
                         (list 121.962 10.4243) 
                         (list 121.923 10.4168) 
                         (list 121.923 10.386) 
                         (list 121.929 10.3756) 
                         (list 122.276 10.3706) 
                         (list 122.288 10.381) 
                         (list 122.288 10.4089) 
                         (list 122.278 10.4243) 
                         (list 122.134 10.4273) 
                         (list 122.119 10.4502) 
                         (list 122.108 10.476) 
                         (list 122.101 11.1489) 
                         (list 122.108 11.1464) 
                         (list 122.466 10.3989) 
                         (list 122.486 10.3756) 
                         (list 122.566 10.3781) 
                         (list 122.931 11.136) 
                         (list 122.944 11.1564) 
                         (list 122.954 11.1281) 
                         (list 122.956 10.4398) 
                         (list 122.954 10.4298) 
                         (list 122.818 10.4273) 
                         "c"
         )
        (command "pline" (list 118.292 11.231) "w" 0 0 
                         (list 118.295 11.1798) 
                         (list 118.349 11.1768) 
                         (list 118.377 11.1718) 
                         (list 118.38 10.4193) 
                         (list 118.372 10.4089) 
                         (list 118.223 10.4089) 
                         (list 118.218 10.3989) 
                         (list 118.218 10.3656) 
                         (list 118.231 10.3577) 
                         (list 118.249 10.3527) 
                         (list 118.909 10.3552) 
                         (list 118.925 10.3656) 
                         (list 118.927 10.4014) 
                         (list 118.912 10.4168) 
                         (list 118.734 10.4193) 
                         (list 118.732 10.7148) 
                         (list 118.737 10.7431) 
                         (list 118.745 10.7531) 
                         (list 118.77 10.7531) 
                         (list 118.804 10.756) 
                         (list 118.832 10.756) 
                         (list 118.942 10.7585) 
                         (list 119.03 10.761) 
                         (list 119.125 10.7585) 
                         (list 119.181 10.7714) 
                         (list 119.271 10.7868) 
                         (list 119.341 10.8123) 
                         (list 119.41 10.8535) 
                         (list 119.451 10.8943) 
                         (list 119.48 10.9406) 
                         (list 119.482 10.9714) 
                         (list 119.487 11.0152) 
                         (list 119.472 11.0614) 
                         (list 119.454 11.1002) 
                         (list 119.426 11.136) 
                         (list 119.366 11.1668) 
                         (list 119.315 11.1923) 
                         (list 119.253 11.2052) 
                         (list 119.187 11.2131) 
                         (list 119.155 11.2152) 
                         (list 118.727 11.1743) 
                         (list 118.84 11.1768) 
                         (list 118.904 11.1823) 
                         (list 118.984 11.1768) 
                         (list 119.043 11.1564) 
                         (list 119.071 11.1231) 
                         (list 119.089 11.0818) 
                         (list 119.097 11.0356) 
                         (list 119.094 10.9793) 
                         (list 119.099 10.9331) 
                         (list 119.089 10.8918) 
                         (list 119.089 10.8818) 
                         (list 119.061 10.8327) 
                         (list 119.03 10.8173) 
                         (list 119.009 10.8123) 
                         (list 118.948 10.8123) 
                         (list 118.734 10.8123) 
                         (list 118.734 10.8202) 
                         (list 118.727 11.1743) 
                         (list 119.155 11.2152) 
                         (list 119.107 11.2181) 
                         (list 119.035 11.2285) 
                         (list 118.95 11.231) 
                         (list 118.86 11.236) 
                         "c"
         )
        (command "pline" (list 121.859 10.3602) "w" 0 0 
                         (list 121.872 10.386) 
                         (list 121.862 10.4193) 
                         (list 121.795 10.4298) 
                         (list 121.777 10.4606) 
                         (list 121.777 10.5193) 
                         (list 121.769 10.5656) 
                         (list 121.759 10.6248) 
                         (list 121.744 10.6735) 
                         (list 121.705 10.7173) 
                         (list 121.664 10.7456) 
                         (list 121.597 10.7814) 
                         (list 121.53 10.7968) 
                         (list 121.499 10.8073) 
                         (list 121.43 10.8123) 
                         (list 121.384 10.8202) 
                         (list 121.376 10.8227) 
                         (list 121.417 10.8277) 
                         (list 121.474 10.8327) 
                         (list 121.553 10.8431) 
                         (list 121.62 10.8585) 
                         (list 121.697 10.8843) 
                         (list 121.764 10.9281) 
                         (list 121.795 10.9689) 
                         (list 121.826 11.046) 
                         (list 121.813 11.1002) 
                         (list 121.774 11.1435) 
                         (list 121.726 11.1743) 
                         (list 121.722 11.176) 
                         (list 121.427 11.0302) 
                         (list 121.428 10.9406) 
                         (list 121.418 10.9098) 
                         (list 121.407 10.8973) 
                         (list 121.379 10.8714) 
                         (list 121.354 10.8664) 
                         (list 121.325 10.861) 
                         (list 121.256 10.8585) 
                         (list 121.089 10.8635) 
                         (list 121.073 10.8764) 
                         (list 121.079 11.1768) 
                         (list 121.089 11.1848) 
                         (list 121.32 11.1848) 
                         (list 121.364 11.1798) 
                         (list 121.389 11.1643) 
                         (list 121.402 11.1464) 
                         (list 121.41 11.1231) 
                         (list 121.418 11.1077) 
                         (list 121.425 11.0923) 
                         (list 121.427 11.0302) 
                         (list 121.722 11.176) 
                         (list 121.649 11.2052) 
                         (list 121.625 11.2131) 
                         (list 121.497 11.2285) 
                         (list 121.438 11.2285) 
                         (list 121.332 11.2385) 
                         (list 121.145 11.2439) 
                         (list 120.595 11.2385) 
                         (list 120.574 11.236) 
                         (list 120.572 11.1898) 
                         (list 120.595 11.1848) 
                         (list 120.723 11.1823) 
                         (list 120.731 10.4193) 
                         (list 120.603 10.4218) 
                         (list 120.605 10.5477) 
                         (list 120.605 10.581) 
                         (list 120.616 10.5864) 
                         (list 120.61 10.6581) 
                         (list 120.592 10.6635) 
                         (list 120.541 10.666) 
                         (list 120.515 10.6018) 
                         (list 120.485 10.5452) 
                         (list 120.433 10.4939) 
                         (list 120.395 10.4606) 
                         (list 120.361 10.4477) 
                         (list 120.302 10.4348) 
                         (list 120.243 10.4143) 
                         (list 120.127 10.4143) 
                         (list 119.917 10.4168) 
                         (list 119.904 10.4323) 
                         (list 119.902 10.7893) 
                         (list 119.956 10.7764) 
                         (list 120.015 10.766) 
                         (list 120.082 10.7531) 
                         (list 120.141 10.7327) 
                         (list 120.161 10.7018) 
                         (list 120.177 10.671) 
                         (list 120.179 10.6198) 
                         (list 120.192 10.6118) 
                         (list 120.259 10.6093) 
                         (list 120.264 10.6198) 
                         (list 120.261 10.9973) 
                         (list 120.249 11.0023) 
                         (list 120.187 10.9998) 
                         (list 120.174 10.9923) 
                         (list 120.169 10.9589) 
                         (list 120.164 10.9331) 
                         (list 120.154 10.9048) 
                         (list 120.128 10.8893) 
                         (list 120.1 10.8664) 
                         (list 120.087 10.856) 
                         (list 120.033 10.851) 
                         (list 119.997 10.8481) 
                         (list 119.904 10.8481) 
                         (list 119.904 11.1848) 
                         (list 120.03 11.1873) 
                         (list 120.1 11.1823) 
                         (list 120.202 11.1823) 
                         (list 120.254 11.1718) 
                         (list 120.3 11.1614) 
                         (list 120.336 11.1464) 
                         (list 120.369 11.1181) 
                         (list 120.408 11.0743) 
                         (list 120.434 11.0485) 
                         (list 120.459 11.0152) 
                         (list 120.482 10.9998) 
                         (list 120.516 10.9948) 
                         (list 120.549 10.9998) 
                         (list 120.549 11.041) 
                         (list 120.549 11.2385) 
                         (list 119.416 11.236) 
                         (list 119.411 11.2231) 
                         (list 119.413 11.1923) 
                         (list 119.424 11.1768) 
                         (list 119.552 11.1768) 
                         (list 119.552 10.4218) 
                         (list 119.398 10.4168) 
                         (list 119.393 10.3989) 
                         (list 119.39 10.3681) 
                         (list 119.411 10.3627) 
                         (list 121.258 10.3681) 
                         (list 121.266 10.3781) 
                         (list 121.264 10.4143) 
                         (list 121.256 10.4218) 
                         (list 121.089 10.4243) 
                         (list 121.081 10.7968) 
                         (list 121.089 10.8048) 
                         (list 121.181 10.7993) 
                         (list 121.233 10.7943) 
                         (list 121.271 10.7814) 
                         (list 121.312 10.761) 
                         (list 121.336 10.7406) 
                         (list 121.359 10.6993) 
                         (list 121.372 10.676) 
                         (list 121.377 10.6352) 
                         (list 121.384 10.576) 
                         (list 121.387 10.5273) 
                         (list 121.405 10.4631) 
                         (list 121.433 10.4348) 
                         (list 121.474 10.4014) 
                         (list 121.533 10.3756) 
                         (list 121.603 10.3577) 
                         (list 121.641 10.3502) 
                         (list 121.857 10.3552) 
                         "c"
         )
        (command "pline" (list 0.0 0.0) "w" 0 0 
                         (list 152.4 0.0) 
                         (list 152.4 152.4) 
                         (list 0.0 152.4) 
                         "c"
         )

  

        (command "pline" (list 140.53 103.128) "w" 0 0 
                         (list 140.527 103.111) 
                         (list 140.533 103.103) 
                         (list 140.524 103.044) 
                         (list 140.513 103.046) 
                         (list 140.525 103.03) 
                         (list 140.541 103.042) 
                         (list 140.531 103.043) 
                         (list 140.54 103.102) 
                         (list 140.548 103.108) 
                         (list 140.551 103.125) 
                         "c"
         )
        (command "pline" (list 141.13 102.541) "w" 0 0 
                         (list 141.111 102.541) 
                         (list 141.104 102.534) 
                         (list 141.04 102.534) 
                         (list 141.04 102.545) 
                         (list 141.025 102.53) 
                         (list 141.04 102.515) 
                         (list 141.04 102.526) 
                         (list 141.104 102.526) 
                         (list 141.111 102.519) 
                         (list 141.13 102.519) 
                         "c"
         )
        (command "pline" (list 141.127 102.683) "w" 0 0 
                         (list 141.108 102.68) 
                         (list 141.102 102.671) 
                         (list 141.039 102.661) 
                         (list 141.037 102.672) 
                         (list 141.025 102.655) 
                         (list 141.042 102.643) 
                         (list 141.04 102.654) 
                         (list 141.103 102.664) 
                         (list 141.112 102.657) 
                         (list 141.13 102.66) 
                         "c"
         )
        (command "pline" (list 141.121 102.823) "w" 0 0 
                         (list 141.104 102.817) 
                         (list 141.099 102.808) 
                         (list 141.038 102.788) 
                         (list 141.035 102.799) 
                         (list 141.025 102.78) 
                         (list 141.044 102.77) 
                         (list 141.04 102.781) 
                         (list 141.101 102.801) 
                         (list 141.111 102.796) 
                         (list 141.128 102.802) 
                         "c"
         )
        (command "pline" (list 141.113 102.963) "w" 0 0 
                         (list 141.097 102.954) 
                         (list 141.093 102.944) 
                         (list 141.037 102.915) 
                         (list 141.032 102.925) 
                         (list 141.025 102.905) 
                         (list 141.045 102.898) 
                         (list 141.04 102.908) 
                         (list 141.097 102.937) 
                         (list 141.107 102.934) 
                         (list 141.124 102.943) 
                         "c"
         )
        (command "pline" (list 141.103 103.101) "w" 0 0 
                         (list 141.088 103.09) 
                         (list 141.087 103.079) 
                         (list 141.035 103.042) 
                         (list 141.028 103.051) 
                         (list 141.025 103.03) 
                         (list 141.046 103.027) 
                         (list 141.039 103.036) 
                         (list 141.091 103.073) 
                         (list 141.101 103.072) 
                         (list 141.117 103.083) 
                         "c"
         )
        (command "pline" (list 141.091 103.237) "w" 0 0 
                         (list 141.078 103.224) 
                         (list 141.078 103.213) 
                         (list 141.033 103.168) 
                         (list 141.025 103.176) 
                         (list 141.025 103.155) 
                         (list 141.046 103.155) 
                         (list 141.038 103.163) 
                         (list 141.083 103.208) 
                         (list 141.094 103.208) 
                         (list 141.107 103.221) 
                         "c"
         )
        (command "pline" (list 140.953 103.247) "w" 0 0 
                         (list 140.942 103.231) 
                         (list 140.943 103.221) 
                         (list 140.906 103.169) 
                         (list 140.897 103.176) 
                         (list 140.9 103.155) 
                         (list 140.921 103.158) 
                         (list 140.912 103.165) 
                         (list 140.949 103.217) 
                         (list 140.96 103.218) 
                         (list 140.971 103.233) 
                         "c"
         )
        (command "pline" (list 140.813 103.254) "w" 0 0 
                         (list 140.804 103.237) 
                         (list 140.807 103.227) 
                         (list 140.778 103.17) 
                         (list 140.768 103.175) 
                         (list 140.775 103.155) 
                         (list 140.795 103.162) 
                         (list 140.785 103.167) 
                         (list 140.814 103.223) 
                         (list 140.824 103.227) 
                         (list 140.833 103.243) 
                         "c"
         )
        (command "pline" (list 140.672 103.258) "w" 0 0 
                         (list 140.666 103.241) 
                         (list 140.671 103.231) 
                         (list 140.651 103.17) 
                         (list 140.64 103.174) 
                         (list 140.65 103.155) 
                         (list 140.669 103.165) 
                         (list 140.658 103.168) 
                         (list 140.678 103.229) 
                         (list 140.687 103.234) 
                         (list 140.693 103.251) 
                         "c"
         )
        (command "pline" (list 140.53 103.26) "w" 0 0 
                         (list 140.527 103.242) 
                         (list 140.534 103.233) 
                         (list 140.524 103.17) 
                         (list 140.513 103.172) 
                         (list 140.525 103.155) 
                         (list 140.542 103.167) 
                         (list 140.531 103.169) 
                         (list 140.541 103.232) 
                         (list 140.55 103.238) 
                         (list 140.553 103.257) 
                         "c"
         )
        (command "pline" (list 139.935 102.674) "w" 0 0 
                         (list 139.951 102.669) 
                         (list 139.959 102.673) 
                         (list 140.012 102.656) 
                         (list 140.009 102.647) 
                         (list 140.025 102.655) 
                         (list 140.017 102.671) 
                         (list 140.014 102.662) 
                         (list 139.961 102.679) 
                         (list 139.957 102.687) 
                         (list 139.941 102.692) 
                         "c"
         )
        (command "pline" (list 139.802 102.66) "w" 0 0 
                         (list 139.819 102.657) 
                         (list 139.827 102.663) 
                         (list 139.886 102.654) 
                         (list 139.884 102.643) 
                         (list 139.9 102.655) 
                         (list 139.888 102.671) 
                         (list 139.887 102.661) 
                         (list 139.828 102.67) 
                         (list 139.822 102.678) 
                         (list 139.805 102.681) 
                         "c"
         )
        (command "pline" (list 139.67 102.66) "w" 0 0 
                         (list 139.688 102.657) 
                         (list 139.697 102.664) 
                         (list 139.76 102.654) 
                         (list 139.758 102.643) 
                         (list 139.775 102.655) 
                         (list 139.763 102.672) 
                         (list 139.761 102.661) 
                         (list 139.698 102.671) 
                         (list 139.692 102.68) 
                         (list 139.673 102.683) 
                         "c"
         )
        (command "pline" (list 140.392 102.732) "w" 0 0 
                         (list 140.392 102.718) 
                         (list 140.397 102.713) 
                         (list 140.397 102.666) 
                         (list 140.389 102.666) 
                         (list 140.4 102.655) 
                         (list 140.411 102.666) 
                         (list 140.403 102.666) 
                         (list 140.403 102.713) 
                         (list 140.408 102.718) 
                         (list 140.408 102.732) 
                         "c"
         )
        (command "pline" (list 140.215 102.704) "w" 0 0 
                         (list 140.224 102.694) 
                         (list 140.232 102.694) 
                         (list 140.265 102.661) 
                         (list 140.259 102.655) 
                         (list 140.275 102.655) 
                         (list 140.275 102.671) 
                         (list 140.269 102.665) 
                         (list 140.236 102.698) 
                         (list 140.236 102.706) 
                         (list 140.226 102.715) 
                         "c"
         )
        (command "pline" (list 140.071 102.685) "w" 0 0 
                         (list 140.084 102.678) 
                         (list 140.093 102.681) 
                         (list 140.138 102.658) 
                         (list 140.134 102.65) 
                         (list 140.15 102.655) 
                         (list 140.145 102.671) 
                         (list 140.141 102.663) 
                         (list 140.095 102.686) 
                         (list 140.093 102.694) 
                         (list 140.079 102.701) 
                         "c"
         )
        (command "pline" (list 140.391 102.864) "w" 0 0 
                         (list 140.391 102.849) 
                         (list 140.397 102.843) 
                         (list 140.397 102.792) 
                         (list 140.388 102.792) 
                         (list 140.4 102.78) 
                         (list 140.412 102.792) 
                         (list 140.403 102.792) 
                         (list 140.403 102.843) 
                         (list 140.409 102.849) 
                         (list 140.409 102.864) 
                         "c"
         )
        (command "pline" (list 140.229 102.851) "w" 0 0 
                         (list 140.236 102.837) 
                         (list 140.244 102.835) 
                         (list 140.267 102.789) 
                         (list 140.259 102.785) 
                         (list 140.275 102.78) 
                         (list 140.28 102.796) 
                         (list 140.272 102.792) 
                         (list 140.249 102.837) 
                         (list 140.252 102.846) 
                         (list 140.245 102.859) 
                         "c"
         )
        (command "pline" (list 140.084 102.833) "w" 0 0 
                         (list 140.095 102.822) 
                         (list 140.103 102.822) 
                         (list 140.139 102.786) 
                         (list 140.133 102.78) 
                         (list 140.15 102.78) 
                         (list 140.15 102.797) 
                         (list 140.144 102.791) 
                         (list 140.108 102.827) 
                         (list 140.108 102.835) 
                         (list 140.097 102.846) 
                         "c"
         )
        (command "pline" (list 139.946 102.826) "w" 0 0 
                         (list 139.959 102.816) 
                         (list 139.968 102.817) 
                         (list 140.013 102.785) 
                         (list 140.007 102.777) 
                         (list 140.025 102.78) 
                         (list 140.022 102.798) 
                         (list 140.016 102.79) 
                         (list 139.972 102.823) 
                         (list 139.97 102.832) 
                         (list 139.957 102.841) 
                         "c"
         )
        (command "pline" (list 139.804 102.8) "w" 0 0 
                         (list 139.82 102.795) 
                         (list 139.829 102.799) 
                         (list 139.886 102.781) 
                         (list 139.882 102.771) 
                         (list 139.9 102.78) 
                         (list 139.891 102.798) 
                         (list 139.888 102.788) 
                         (list 139.831 102.806) 
                         (list 139.827 102.815) 
                         (list 139.81 102.82) 
                         "c"
         )
        (command "pline" (list 139.672 102.802) "w" 0 0 
                         (list 139.689 102.796) 
                         (list 139.699 102.801) 
                         (list 139.76 102.781) 
                         (list 139.756 102.77) 
                         (list 139.775 102.78) 
                         (list 139.765 102.799) 
                         (list 139.762 102.788) 
                         (list 139.701 102.808) 
                         (list 139.696 102.817) 
                         (list 139.679 102.823) 
                         "c"
         )
        (command "pline" (list 140.39 102.996) "w" 0 0 
                         (list 140.39 102.98) 
                         (list 140.397 102.973) 
                         (list 140.397 102.918) 
                         (list 140.387 102.918) 
                         (list 140.4 102.905) 
                         (list 140.413 102.918) 
                         (list 140.403 102.918) 
                         (list 140.403 102.973) 
                         (list 140.41 102.98) 
                         (list 140.41 102.996) 
                         "c"
         )
        (command "pline" (list 140.238 102.989) "w" 0 0 
                         (list 140.243 102.973) 
                         (list 140.251 102.969) 
                         (list 140.268 102.916) 
                         (list 140.259 102.913) 
                         (list 140.275 102.905) 
                         (list 140.283 102.921) 
                         (list 140.274 102.918) 
                         (list 140.257 102.971) 
                         (list 140.261 102.979) 
                         (list 140.256 102.995) 
                         "c"
         )
        (command "pline" (list 140.089 102.973) "w" 0 0 
                         (list 140.098 102.96) 
                         (list 140.107 102.958) 
                         (list 140.14 102.914) 
                         (list 140.132 102.908) 
                         (list 140.15 102.905) 
                         (list 140.153 102.923) 
                         (list 140.145 102.917) 
                         (list 140.113 102.962) 
                         (list 140.114 102.971) 
                         (list 140.104 102.984) 
                         "c"
         )
        (command "pline" (list 139.954 102.962) "w" 0 0 
                         (list 139.965 102.951) 
                         (list 139.974 102.951) 
                         (list 140.014 102.912) 
                         (list 140.007 102.905) 
                         (list 140.025 102.905) 
                         (list 140.025 102.923) 
                         (list 140.018 102.916) 
                         (list 139.979 102.956) 
                         (list 139.979 102.965) 
                         (list 139.968 102.976) 
                         "c"
         )
        (command "pline" (list 139.808 102.94) "w" 0 0 
                         (list 139.824 102.932) 
                         (list 139.833 102.935) 
                         (list 139.886 102.908) 
                         (list 139.881 102.899) 
                         (list 139.9 102.905) 
                         (list 139.894 102.924) 
                         (list 139.889 102.914) 
                         (list 139.836 102.941) 
                         (list 139.833 102.951) 
                         (list 139.817 102.959) 
                         "c"
         )
        (command "pline" (list 139.676 102.943) "w" 0 0 
                         (list 139.693 102.934) 
                         (list 139.703 102.937) 
                         (list 139.76 102.908) 
                         (list 139.755 102.898) 
                         (list 139.775 102.905) 
                         (list 139.768 102.925) 
                         (list 139.763 102.915) 
                         (list 139.707 102.944) 
                         (list 139.703 102.954) 
                         (list 139.687 102.963) 
                         "c"
         )
        (command "pline" (list 139.823 103.092) "w" 0 0 
                         (list 139.836 103.079) 
                         (list 139.846 103.079) 
                         (list 139.888 103.037) 
                         (list 139.88 103.03) 
                         (list 139.9 103.03) 
                         (list 139.9 103.05) 
                         (list 139.893 103.042) 
                         (list 139.851 103.084) 
                         (list 139.851 103.094) 
                         (list 139.838 103.107) 
                         "c"
         )
        (command "pline" (list 139.683 103.083) "w" 0 0 
                         (list 139.699 103.072) 
                         (list 139.709 103.073) 
                         (list 139.761 103.036) 
                         (list 139.754 103.027) 
                         (list 139.775 103.03) 
                         (list 139.772 103.051) 
                         (list 139.765 103.042) 
                         (list 139.713 103.079) 
                         (list 139.712 103.09) 
                         (list 139.697 103.101) 
                         "c"
         )
        (command "pline" (list 140.39 103.128) "w" 0 0 
                         (list 140.39 103.111) 
                         (list 140.397 103.104) 
                         (list 140.397 103.044) 
                         (list 140.386 103.044) 
                         (list 140.4 103.03) 
                         (list 140.414 103.044) 
                         (list 140.404 103.044) 
                         (list 140.404 103.104) 
                         (list 140.411 103.111) 
                         (list 140.411 103.128) 
                         "c"
         )
        (command "pline" (list 140.249 103.125) "w" 0 0 
                         (list 140.252 103.108) 
                         (list 140.26 103.102) 
                         (list 140.269 103.043) 
                         (list 140.259 103.042) 
                         (list 140.275 103.03) 
                         (list 140.287 103.046) 
                         (list 140.276 103.044) 
                         (list 140.267 103.103) 
                         (list 140.273 103.111) 
                         (list 140.27 103.128) 
                         "c"
         )
        (command "pline" (list 140.11 103.12) "w" 0 0 
                         (list 140.115 103.103) 
                         (list 140.124 103.099) 
                         (list 140.142 103.042) 
                         (list 140.132 103.039) 
                         (list 140.15 103.03) 
                         (list 140.159 103.048) 
                         (list 140.149 103.044) 
                         (list 140.131 103.101) 
                         (list 140.135 103.11) 
                         (list 140.13 103.126) 
                         "c"
         )
        (command "pline" (list 139.971 103.113) "w" 0 0 
                         (list 139.979 103.097) 
                         (list 139.989 103.094) 
                         (list 140.016 103.041) 
                         (list 140.006 103.036) 
                         (list 140.025 103.03) 
                         (list 140.031 103.049) 
                         (list 140.022 103.044) 
                         (list 139.995 103.097) 
                         (list 139.998 103.106) 
                         (list 139.99 103.122) 
                         "c"
         )
        (command "pline" (list 140.389 103.26) "w" 0 0 
                         (list 140.389 103.241) 
                         (list 140.396 103.234) 
                         (list 140.396 103.17) 
                         (list 140.385 103.17) 
                         (list 140.4 103.155) 
                         (list 140.415 103.17) 
                         (list 140.404 103.17) 
                         (list 140.404 103.234) 
                         (list 140.411 103.241) 
                         (list 140.411 103.26) 
                         "c"
         )
        (command "pline" (list 140.247 103.257) "w" 0 0 
                         (list 140.25 103.238) 
                         (list 140.259 103.232) 
                         (list 140.269 103.169) 
                         (list 140.258 103.167) 
                         (list 140.275 103.155) 
                         (list 140.287 103.172) 
                         (list 140.276 103.17) 
                         (list 140.266 103.233) 
                         (list 140.273 103.242) 
                         (list 140.27 103.26) 
                         "c"
         )
        (command "pline" (list 140.107 103.251) "w" 0 0 
                         (list 140.113 103.234) 
                         (list 140.122 103.229) 
                         (list 140.142 103.168) 
                         (list 140.131 103.165) 
                         (list 140.15 103.155) 
                         (list 140.16 103.174) 
                         (list 140.149 103.17) 
                         (list 140.129 103.231) 
                         (list 140.134 103.241) 
                         (list 140.128 103.258) 
                         "c"
         )
        (command "pline" (list 139.967 103.243) "w" 0 0 
                         (list 139.976 103.227) 
                         (list 139.986 103.223) 
                         (list 140.015 103.167) 
                         (list 140.005 103.162) 
                         (list 140.025 103.155) 
                         (list 140.032 103.175) 
                         (list 140.022 103.17) 
                         (list 139.993 103.227) 
                         (list 139.996 103.237) 
                         (list 139.987 103.254) 
                         "c"
         )
        (command "pline" (list 139.829 103.233) "w" 0 0 
                         (list 139.84 103.218) 
                         (list 139.851 103.217) 
                         (list 139.888 103.165) 
                         (list 139.879 103.158) 
                         (list 139.9 103.155) 
                         (list 139.903 103.176) 
                         (list 139.894 103.169) 
                         (list 139.857 103.221) 
                         (list 139.858 103.231) 
                         (list 139.847 103.247) 
                         "c"
         )
        (command "pline" (list 139.693 103.221) "w" 0 0 
                         (list 139.706 103.208) 
                         (list 139.717 103.208) 
                         (list 139.762 103.163) 
                         (list 139.754 103.155) 
                         (list 139.775 103.155) 
                         (list 139.775 103.176) 
                         (list 139.767 103.168) 
                         (list 139.722 103.213) 
                         (list 139.722 103.224) 
                         (list 139.709 103.237) 
                         "c"
         )
        (command "pline" (list 140.256 102.065) "w" 0 0 
                         (list 140.261 102.081) 
                         (list 140.257 102.089) 
                         (list 140.274 102.142) 
                         (list 140.283 102.139) 
                         (list 140.275 102.155) 
                         (list 140.259 102.147) 
                         (list 140.268 102.144) 
                         (list 140.251 102.091) 
                         (list 140.243 102.087) 
                         (list 140.238 102.071) 
                         "c"
         )
        (command "pline" (list 140.27 101.932) "w" 0 0 
                         (list 140.273 101.949) 
                         (list 140.267 101.957) 
                         (list 140.276 102.016) 
                         (list 140.287 102.014) 
                         (list 140.275 102.03) 
                         (list 140.259 102.018) 
                         (list 140.269 102.017) 
                         (list 140.26 101.958) 
                         (list 140.252 101.952) 
                         (list 140.249 101.935) 
                         "c"
         )
        (command "pline" (list 140.27 101.8) "w" 0 0 
                         (list 140.273 101.818) 
                         (list 140.266 101.827) 
                         (list 140.276 101.89) 
                         (list 140.287 101.888) 
                         (list 140.275 101.905) 
                         (list 140.258 101.893) 
                         (list 140.269 101.891) 
                         (list 140.259 101.828) 
                         (list 140.25 101.822) 
                         (list 140.247 101.803) 
                         "c"
         )
        (command "pline" (list 140.198 102.522) "w" 0 0 
                         (list 140.212 102.522) 
                         (list 140.217 102.527) 
                         (list 140.264 102.527) 
                         (list 140.264 102.519) 
                         (list 140.275 102.53) 
                         (list 140.264 102.541) 
                         (list 140.264 102.533) 
                         (list 140.217 102.533) 
                         (list 140.212 102.538) 
                         (list 140.198 102.538) 
                         "c"
         )
        (command "pline" (list 140.226 102.345) "w" 0 0 
                         (list 140.236 102.354) 
                         (list 140.236 102.362) 
                         (list 140.269 102.395) 
                         (list 140.275 102.389) 
                         (list 140.275 102.405) 
                         (list 140.259 102.405) 
                         (list 140.265 102.399) 
                         (list 140.232 102.366) 
                         (list 140.224 102.366) 
                         (list 140.215 102.356) 
                         "c"
         )
        (command "pline" (list 140.245 102.201) "w" 0 0 
                         (list 140.252 102.214) 
                         (list 140.249 102.223) 
                         (list 140.272 102.268) 
                         (list 140.28 102.264) 
                         (list 140.275 102.28) 
                         (list 140.259 102.275) 
                         (list 140.267 102.271) 
                         (list 140.244 102.225) 
                         (list 140.236 102.223) 
                         (list 140.229 102.209) 
                         "c"
         )
        (command "pline" (list 140.066 102.521) "w" 0 0 
                         (list 140.081 102.521) 
                         (list 140.087 102.527) 
                         (list 140.138 102.527) 
                         (list 140.138 102.518) 
                         (list 140.15 102.53) 
                         (list 140.138 102.542) 
                         (list 140.138 102.533) 
                         (list 140.087 102.533) 
                         (list 140.081 102.539) 
                         (list 140.066 102.539) 
                         "c"
         )
        (command "pline" (list 140.079 102.359) "w" 0 0 
                         (list 140.093 102.366) 
                         (list 140.095 102.374) 
                         (list 140.141 102.397) 
                         (list 140.145 102.389) 
                         (list 140.15 102.405) 
                         (list 140.134 102.41) 
                         (list 140.138 102.402) 
                         (list 140.093 102.379) 
                         (list 140.084 102.382) 
                         (list 140.071 102.375) 
                         "c"
         )
        (command "pline" (list 140.097 102.214) "w" 0 0 
                         (list 140.108 102.225) 
                         (list 140.108 102.233) 
                         (list 140.144 102.269) 
                         (list 140.15 102.263) 
                         (list 140.15 102.28) 
                         (list 140.133 102.28) 
                         (list 140.139 102.274) 
                         (list 140.103 102.238) 
                         (list 140.095 102.238) 
                         (list 140.084 102.227) 
                         "c"
         )
        (command "pline" (list 140.104 102.076) "w" 0 0 
                         (list 140.114 102.089) 
                         (list 140.113 102.098) 
                         (list 140.145 102.143) 
                         (list 140.153 102.137) 
                         (list 140.15 102.155) 
                         (list 140.132 102.152) 
                         (list 140.14 102.146) 
                         (list 140.107 102.102) 
                         (list 140.098 102.1) 
                         (list 140.089 102.087) 
                         "c"
         )
        (command "pline" (list 140.13 101.934) "w" 0 0 
                         (list 140.135 101.95) 
                         (list 140.131 101.959) 
                         (list 140.149 102.016) 
                         (list 140.159 102.012) 
                         (list 140.15 102.03) 
                         (list 140.132 102.021) 
                         (list 140.142 102.018) 
                         (list 140.124 101.961) 
                         (list 140.115 101.957) 
                         (list 140.11 101.94) 
                         "c"
         )
        (command "pline" (list 140.128 101.802) "w" 0 0 
                         (list 140.134 101.819) 
                         (list 140.129 101.829) 
                         (list 140.149 101.89) 
                         (list 140.16 101.886) 
                         (list 140.15 101.905) 
                         (list 140.131 101.895) 
                         (list 140.142 101.892) 
                         (list 140.122 101.831) 
                         (list 140.113 101.826) 
                         (list 140.107 101.809) 
                         "c"
         )
        (command "pline" (list 139.934 102.52) "w" 0 0 
                         (list 139.95 102.52) 
                         (list 139.957 102.527) 
                         (list 140.012 102.527) 
                         (list 140.012 102.517) 
                         (list 140.025 102.53) 
                         (list 140.012 102.543) 
                         (list 140.012 102.533) 
                         (list 139.957 102.533) 
                         (list 139.95 102.54) 
                         (list 139.934 102.54) 
                         "c"
         )
        (command "pline" (list 139.941 102.368) "w" 0 0 
                         (list 139.957 102.373) 
                         (list 139.961 102.381) 
                         (list 140.014 102.398) 
                         (list 140.017 102.389) 
                         (list 140.025 102.405) 
                         (list 140.009 102.413) 
                         (list 140.012 102.404) 
                         (list 139.959 102.387) 
                         (list 139.951 102.391) 
                         (list 139.935 102.386) 
                         "c"
         )
        (command "pline" (list 139.957 102.219) "w" 0 0 
                         (list 139.97 102.228) 
                         (list 139.972 102.237) 
                         (list 140.016 102.27) 
                         (list 140.022 102.262) 
                         (list 140.025 102.28) 
                         (list 140.007 102.283) 
                         (list 140.013 102.275) 
                         (list 139.968 102.243) 
                         (list 139.959 102.244) 
                         (list 139.946 102.234) 
                         "c"
         )
        (command "pline" (list 139.968 102.084) "w" 0 0 
                         (list 139.979 102.095) 
                         (list 139.979 102.104) 
                         (list 140.018 102.144) 
                         (list 140.025 102.137) 
                         (list 140.025 102.155) 
                         (list 140.007 102.155) 
                         (list 140.014 102.148) 
                         (list 139.974 102.109) 
                         (list 139.965 102.109) 
                         (list 139.954 102.098) 
                         "c"
         )
        (command "pline" (list 139.99 101.938) "w" 0 0 
                         (list 139.998 101.954) 
                         (list 139.995 101.963) 
                         (list 140.022 102.016) 
                         (list 140.031 102.011) 
                         (list 140.025 102.03) 
                         (list 140.006 102.024) 
                         (list 140.016 102.019) 
                         (list 139.989 101.966) 
                         (list 139.979 101.963) 
                         (list 139.971 101.947) 
                         "c"
         )
        (command "pline" (list 139.987 101.806) "w" 0 0 
                         (list 139.996 101.823) 
                         (list 139.993 101.833) 
                         (list 140.022 101.89) 
                         (list 140.032 101.885) 
                         (list 140.025 101.905) 
                         (list 140.005 101.898) 
                         (list 140.015 101.893) 
                         (list 139.986 101.837) 
                         (list 139.976 101.833) 
                         (list 139.967 101.817) 
                         "c"
         )
        (command "pline" (list 139.838 101.953) "w" 0 0 
                         (list 139.851 101.966) 
                         (list 139.851 101.976) 
                         (list 139.893 102.018) 
                         (list 139.9 102.01) 
                         (list 139.9 102.03) 
                         (list 139.88 102.03) 
                         (list 139.888 102.023) 
                         (list 139.846 101.981) 
                         (list 139.836 101.981) 
                         (list 139.823 101.968) 
                         "c"
         )
        (command "pline" (list 139.847 101.813) "w" 0 0 
                         (list 139.858 101.829) 
                         (list 139.857 101.839) 
                         (list 139.894 101.891) 
                         (list 139.903 101.884) 
                         (list 139.9 101.905) 
                         (list 139.879 101.902) 
                         (list 139.888 101.895) 
                         (list 139.851 101.843) 
                         (list 139.84 101.842) 
                         (list 139.829 101.827) 
                         "c"
         )
        (command "pline" (list 139.802 102.52) "w" 0 0 
                         (list 139.82 102.52) 
                         (list 139.827 102.527) 
                         (list 139.886 102.527) 
                         (list 139.886 102.516) 
                         (list 139.9 102.53) 
                         (list 139.886 102.544) 
                         (list 139.886 102.534) 
                         (list 139.827 102.534) 
                         (list 139.82 102.54) 
                         (list 139.802 102.54) 
                         "c"
         )
        (command "pline" (list 139.805 102.379) "w" 0 0 
                         (list 139.822 102.382) 
                         (list 139.828 102.39) 
                         (list 139.887 102.399) 
                         (list 139.888 102.389) 
                         (list 139.9 102.405) 
                         (list 139.884 102.417) 
                         (list 139.886 102.406) 
                         (list 139.827 102.397) 
                         (list 139.819 102.403) 
                         (list 139.802 102.4) 
                         "c"
         )
        (command "pline" (list 139.81 102.24) "w" 0 0 
                         (list 139.827 102.245) 
                         (list 139.831 102.254) 
                         (list 139.888 102.272) 
                         (list 139.891 102.262) 
                         (list 139.9 102.28) 
                         (list 139.882 102.289) 
                         (list 139.886 102.279) 
                         (list 139.829 102.261) 
                         (list 139.82 102.265) 
                         (list 139.804 102.26) 
                         "c"
         )
        (command "pline" (list 139.817 102.101) "w" 0 0 
                         (list 139.833 102.109) 
                         (list 139.836 102.119) 
                         (list 139.889 102.146) 
                         (list 139.894 102.136) 
                         (list 139.9 102.155) 
                         (list 139.881 102.161) 
                         (list 139.886 102.152) 
                         (list 139.833 102.125) 
                         (list 139.824 102.128) 
                         (list 139.808 102.12) 
                         "c"
         )
        (command "pline" (list 139.67 102.519) "w" 0 0 
                         (list 139.689 102.519) 
                         (list 139.696 102.526) 
                         (list 139.76 102.526) 
                         (list 139.76 102.515) 
                         (list 139.775 102.53) 
                         (list 139.76 102.545) 
                         (list 139.76 102.534) 
                         (list 139.696 102.534) 
                         (list 139.689 102.541) 
                         (list 139.67 102.541) 
                         "c"
         )
        (command "pline" (list 139.673 102.377) "w" 0 0 
                         (list 139.692 102.38) 
                         (list 139.698 102.389) 
                         (list 139.761 102.399) 
                         (list 139.763 102.388) 
                         (list 139.775 102.405) 
                         (list 139.758 102.417) 
                         (list 139.76 102.406) 
                         (list 139.697 102.396) 
                         (list 139.688 102.403) 
                         (list 139.67 102.4) 
                         "c"
         )
        (command "pline" (list 139.679 102.237) "w" 0 0 
                         (list 139.696 102.243) 
                         (list 139.701 102.252) 
                         (list 139.762 102.272) 
                         (list 139.765 102.261) 
                         (list 139.775 102.28) 
                         (list 139.756 102.29) 
                         (list 139.76 102.279) 
                         (list 139.699 102.259) 
                         (list 139.689 102.264) 
                         (list 139.672 102.258) 
                         "c"
         )
        (command "pline" (list 139.687 102.097) "w" 0 0 
                         (list 139.703 102.106) 
                         (list 139.707 102.116) 
                         (list 139.763 102.145) 
                         (list 139.768 102.135) 
                         (list 139.775 102.155) 
                         (list 139.755 102.162) 
                         (list 139.76 102.152) 
                         (list 139.703 102.123) 
                         (list 139.693 102.126) 
                         (list 139.676 102.117) 
                         "c"
         )
        (command "pline" (list 139.697 101.959) "w" 0 0 
                         (list 139.712 101.97) 
                         (list 139.713 101.981) 
                         (list 139.765 102.018) 
                         (list 139.772 102.009) 
                         (list 139.775 102.03) 
                         (list 139.754 102.033) 
                         (list 139.761 102.024) 
                         (list 139.709 101.987) 
                         (list 139.699 101.988) 
                         (list 139.683 101.977) 
                         "c"
         )
        (command "pline" (list 139.709 101.823) "w" 0 0 
                         (list 139.722 101.836) 
                         (list 139.722 101.847) 
                         (list 139.767 101.892) 
                         (list 139.775 101.884) 
                         (list 139.775 101.905) 
                         (list 139.754 101.905) 
                         (list 139.762 101.897) 
                         (list 139.717 101.852) 
                         (list 139.706 101.852) 
                         (list 139.693 101.839) 
                         "c"
         )
        (command "pline" (list 141.107 101.839) "w" 0 0 
                         (list 141.094 101.852) 
                         (list 141.083 101.852) 
                         (list 141.038 101.897) 
                         (list 141.046 101.905) 
                         (list 141.025 101.905) 
                         (list 141.025 101.884) 
                         (list 141.033 101.892) 
                         (list 141.078 101.847) 
                         (list 141.078 101.836) 
                         (list 141.091 101.823) 
                         "c"
         )
        (command "pline" (list 140.971 101.827) "w" 0 0 
                         (list 140.96 101.842) 
                         (list 140.949 101.843) 
                         (list 140.912 101.895) 
                         (list 140.921 101.902) 
                         (list 140.9 101.905) 
                         (list 140.897 101.884) 
                         (list 140.906 101.891) 
                         (list 140.943 101.839) 
                         (list 140.942 101.829) 
                         (list 140.953 101.813) 
                         "c"
         )
        (command "pline" (list 140.833 101.817) "w" 0 0 
                         (list 140.824 101.833) 
                         (list 140.814 101.837) 
                         (list 140.785 101.893) 
                         (list 140.795 101.898) 
                         (list 140.775 101.905) 
                         (list 140.768 101.885) 
                         (list 140.778 101.89) 
                         (list 140.807 101.833) 
                         (list 140.804 101.823) 
                         (list 140.813 101.806) 
                         "c"
         )
        (command "pline" (list 140.693 101.809) "w" 0 0 
                         (list 140.687 101.826) 
                         (list 140.678 101.831) 
                         (list 140.658 101.892) 
                         (list 140.669 101.895) 
                         (list 140.65 101.905) 
                         (list 140.64 101.886) 
                         (list 140.651 101.89) 
                         (list 140.671 101.829) 
                         (list 140.666 101.819) 
                         (list 140.672 101.802) 
                         "c"
         )
        (command "pline" (list 140.553 101.803) "w" 0 0 
                         (list 140.55 101.822) 
                         (list 140.541 101.828) 
                         (list 140.531 101.891) 
                         (list 140.542 101.893) 
                         (list 140.525 101.905) 
                         (list 140.513 101.888) 
                         (list 140.524 101.89) 
                         (list 140.534 101.827) 
                         (list 140.527 101.818) 
                         (list 140.53 101.8) 
                         "c"
         )
        (command "pline" (list 140.411 101.8) "w" 0 0 
                         (list 140.411 101.819) 
                         (list 140.404 101.826) 
                         (list 140.404 101.89) 
                         (list 140.415 101.89) 
                         (list 140.4 101.905) 
                         (list 140.385 101.89) 
                         (list 140.396 101.89) 
                         (list 140.396 101.826) 
                         (list 140.389 101.819) 
                         (list 140.389 101.8) 
                         "c"
         )
        (command "pline" (list 141.117 101.977) "w" 0 0 
                         (list 141.101 101.988) 
                         (list 141.091 101.987) 
                         (list 141.039 102.024) 
                         (list 141.046 102.033) 
                         (list 141.025 102.03) 
                         (list 141.028 102.009) 
                         (list 141.035 102.018) 
                         (list 141.087 101.981) 
                         (list 141.088 101.97) 
                         (list 141.103 101.959) 
                         "c"
         )
        (command "pline" (list 140.977 101.968) "w" 0 0 
                         (list 140.964 101.981) 
                         (list 140.954 101.981) 
                         (list 140.912 102.023) 
                         (list 140.92 102.03) 
                         (list 140.9 102.03) 
                         (list 140.9 102.01) 
                         (list 140.907 102.018) 
                         (list 140.949 101.976) 
                         (list 140.949 101.966) 
                         (list 140.962 101.953) 
                         "c"
         )
        (command "pline" (list 140.829 101.947) "w" 0 0 
                         (list 140.821 101.963) 
                         (list 140.811 101.966) 
                         (list 140.784 102.019) 
                         (list 140.794 102.024) 
                         (list 140.775 102.03) 
                         (list 140.769 102.011) 
                         (list 140.778 102.016) 
                         (list 140.805 101.963) 
                         (list 140.802 101.954) 
                         (list 140.81 101.938) 
                         "c"
         )
        (command "pline" (list 140.69 101.94) "w" 0 0 
                         (list 140.685 101.957) 
                         (list 140.676 101.961) 
                         (list 140.658 102.018) 
                         (list 140.668 102.021) 
                         (list 140.65 102.03) 
                         (list 140.641 102.012) 
                         (list 140.651 102.016) 
                         (list 140.669 101.959) 
                         (list 140.665 101.95) 
                         (list 140.67 101.934) 
                         "c"
         )
        (command "pline" (list 140.551 101.935) "w" 0 0 
                         (list 140.548 101.952) 
                         (list 140.54 101.958) 
                         (list 140.531 102.017) 
                         (list 140.541 102.018) 
                         (list 140.525 102.03) 
                         (list 140.513 102.014) 
                         (list 140.524 102.016) 
                         (list 140.533 101.957) 
                         (list 140.527 101.949) 
                         (list 140.53 101.932) 
                         "c"
         )
        (command "pline" (list 140.411 101.932) "w" 0 0 
                         (list 140.411 101.95) 
                         (list 140.404 101.957) 
                         (list 140.404 102.016) 
                         (list 140.414 102.016) 
                         (list 140.4 102.03) 
                         (list 140.386 102.016) 
                         (list 140.397 102.016) 
                         (list 140.397 101.957) 
                         (list 140.39 101.95) 
                         (list 140.39 101.932) 
                         "c"
         )
        (command "pline" (list 141.124 102.117) "w" 0 0 
                         (list 141.107 102.126) 
                         (list 141.097 102.123) 
                         (list 141.04 102.152) 
                         (list 141.045 102.162) 
                         (list 141.025 102.155) 
                         (list 141.032 102.135) 
                         (list 141.037 102.145) 
                         (list 141.093 102.116) 
                         (list 141.097 102.106) 
                         (list 141.113 102.097) 
                         "c"
         )
        (command "pline" (list 140.992 102.12) "w" 0 0 
                         (list 140.976 102.128) 
                         (list 140.967 102.125) 
                         (list 140.914 102.152) 
                         (list 140.919 102.161) 
                         (list 140.9 102.155) 
                         (list 140.906 102.136) 
                         (list 140.911 102.146) 
                         (list 140.964 102.119) 
                         (list 140.967 102.109) 
                         (list 140.983 102.101) 
                         "c"
         )
        (command "pline" (list 140.846 102.098) "w" 0 0 
                         (list 140.835 102.109) 
                         (list 140.826 102.109) 
                         (list 140.786 102.148) 
                         (list 140.793 102.155) 
                         (list 140.775 102.155) 
                         (list 140.775 102.137) 
                         (list 140.782 102.144) 
                         (list 140.821 102.104) 
                         (list 140.821 102.095) 
                         (list 140.832 102.084) 
                         "c"
         )
        (command "pline" (list 140.711 102.087) "w" 0 0 
                         (list 140.702 102.1) 
                         (list 140.693 102.102) 
                         (list 140.66 102.146) 
                         (list 140.668 102.152) 
                         (list 140.65 102.155) 
                         (list 140.647 102.137) 
                         (list 140.655 102.143) 
                         (list 140.687 102.098) 
                         (list 140.686 102.089) 
                         (list 140.696 102.076) 
                         "c"
         )
        (command "pline" (list 140.562 102.071) "w" 0 0 
                         (list 140.557 102.087) 
                         (list 140.549 102.091) 
                         (list 140.532 102.144) 
                         (list 140.541 102.147) 
                         (list 140.525 102.155) 
                         (list 140.517 102.139) 
                         (list 140.526 102.142) 
                         (list 140.543 102.089) 
                         (list 140.539 102.081) 
                         (list 140.544 102.065) 
                         "c"
         )
        (command "pline" (list 140.41 102.064) "w" 0 0 
                         (list 140.41 102.08) 
                         (list 140.403 102.087) 
                         (list 140.403 102.142) 
                         (list 140.413 102.142) 
                         (list 140.4 102.155) 
                         (list 140.387 102.142) 
                         (list 140.397 102.142) 
                         (list 140.397 102.087) 
                         (list 140.39 102.08) 
                         (list 140.39 102.064) 
                         "c"
         )
        (command "pline" (list 141.128 102.258) "w" 0 0 
                         (list 141.111 102.264) 
                         (list 141.101 102.259) 
                         (list 141.04 102.279) 
                         (list 141.044 102.29) 
                         (list 141.025 102.28) 
                         (list 141.035 102.261) 
                         (list 141.038 102.272) 
                         (list 141.099 102.252) 
                         (list 141.104 102.243) 
                         (list 141.121 102.237) 
                         "c"
         )
        (command "pline" (list 140.996 102.26) "w" 0 0 
                         (list 140.98 102.265) 
                         (list 140.971 102.261) 
                         (list 140.914 102.279) 
                         (list 140.918 102.289) 
                         (list 140.9 102.28) 
                         (list 140.909 102.262) 
                         (list 140.912 102.272) 
                         (list 140.969 102.254) 
                         (list 140.973 102.245) 
                         (list 140.99 102.24) 
                         "c"
         )
        (command "pline" (list 140.854 102.234) "w" 0 0 
                         (list 140.841 102.244) 
                         (list 140.832 102.243) 
                         (list 140.787 102.275) 
                         (list 140.793 102.283) 
                         (list 140.775 102.28) 
                         (list 140.778 102.262) 
                         (list 140.784 102.27) 
                         (list 140.828 102.237) 
                         (list 140.83 102.228) 
                         (list 140.843 102.219) 
                         "c"
         )
        (command "pline" (list 140.716 102.227) "w" 0 0 
                         (list 140.705 102.238) 
                         (list 140.697 102.238) 
                         (list 140.661 102.274) 
                         (list 140.667 102.28) 
                         (list 140.65 102.28) 
                         (list 140.65 102.263) 
                         (list 140.656 102.269) 
                         (list 140.692 102.233) 
                         (list 140.692 102.225) 
                         (list 140.703 102.214) 
                         "c"
         )
        (command "pline" (list 140.571 102.209) "w" 0 0 
                         (list 140.564 102.223) 
                         (list 140.556 102.225) 
                         (list 140.533 102.271) 
                         (list 140.541 102.275) 
                         (list 140.525 102.28) 
                         (list 140.52 102.264) 
                         (list 140.528 102.268) 
                         (list 140.551 102.223) 
                         (list 140.548 102.214) 
                         (list 140.555 102.201) 
                         "c"
         )
        (command "pline" (list 140.409 102.196) "w" 0 0 
                         (list 140.409 102.211) 
                         (list 140.403 102.217) 
                         (list 140.403 102.268) 
                         (list 140.412 102.268) 
                         (list 140.4 102.28) 
                         (list 140.388 102.268) 
                         (list 140.397 102.268) 
                         (list 140.397 102.217) 
                         (list 140.391 102.211) 
                         (list 140.391 102.196) 
                         "c"
         )
        (command "pline" (list 141.13 102.4) "w" 0 0 
                         (list 141.112 102.403) 
                         (list 141.103 102.396) 
                         (list 141.04 102.406) 
                         (list 141.042 102.417) 
                         (list 141.025 102.405) 
                         (list 141.037 102.388) 
                         (list 141.039 102.399) 
                         (list 141.102 102.389) 
                         (list 141.108 102.38) 
                         (list 141.127 102.377) 
                         "c"
         )
        (command "pline" (list 140.998 102.4) "w" 0 0 
                         (list 140.981 102.403) 
                         (list 140.973 102.397) 
                         (list 140.914 102.406) 
                         (list 140.916 102.417) 
                         (list 140.9 102.405) 
                         (list 140.912 102.389) 
                         (list 140.913 102.399) 
                         (list 140.972 102.39) 
                         (list 140.978 102.382) 
                         (list 140.995 102.379) 
                         "c"
         )
        (command "pline" (list 140.865 102.386) "w" 0 0 
                         (list 140.849 102.391) 
                         (list 140.841 102.387) 
                         (list 140.788 102.404) 
                         (list 140.791 102.413) 
                         (list 140.775 102.405) 
                         (list 140.783 102.389) 
                         (list 140.786 102.398) 
                         (list 140.839 102.381) 
                         (list 140.843 102.373) 
                         (list 140.859 102.368) 
                         "c"
         )
        (command "pline" (list 140.729 102.375) "w" 0 0 
                         (list 140.716 102.382) 
                         (list 140.707 102.379) 
                         (list 140.662 102.402) 
                         (list 140.666 102.41) 
                         (list 140.65 102.405) 
                         (list 140.655 102.389) 
                         (list 140.659 102.397) 
                         (list 140.705 102.374) 
                         (list 140.707 102.366) 
                         (list 140.721 102.359) 
                         "c"
         )
        (command "pline" (list 140.585 102.356) "w" 0 0 
                         (list 140.576 102.366) 
                         (list 140.568 102.366) 
                         (list 140.535 102.399) 
                         (list 140.541 102.405) 
                         (list 140.525 102.405) 
                         (list 140.525 102.389) 
                         (list 140.531 102.395) 
                         (list 140.564 102.362) 
                         (list 140.564 102.354) 
                         (list 140.574 102.345) 
                         "c"
         )
        (command "pline" (list 140.408 102.328) "w" 0 0 
                         (list 140.408 102.342) 
                         (list 140.403 102.347) 
                         (list 140.403 102.394) 
                         (list 140.411 102.394) 
                         (list 140.4 102.405) 
                         (list 140.389 102.394) 
                         (list 140.397 102.394) 
                         (list 140.397 102.347) 
                         (list 140.392 102.342) 
                         (list 140.392 102.328) 
                         "c"
         )
        (command "pline" (list 140.998 102.54) "w" 0 0 
                         (list 140.981 102.54) 
                         (list 140.974 102.534) 
                         (list 140.914 102.534) 
                         (list 140.914 102.544) 
                         (list 140.9 102.53) 
                         (list 140.914 102.516) 
                         (list 140.914 102.527) 
                         (list 140.974 102.527) 
                         (list 140.981 102.52) 
                         (list 140.998 102.52) 
                         "c"
         )
        (command "pline" (list 140.995 102.681) "w" 0 0 
                         (list 140.978 102.678) 
                         (list 140.972 102.67) 
                         (list 140.913 102.661) 
                         (list 140.912 102.671) 
                         (list 140.9 102.655) 
                         (list 140.916 102.643) 
                         (list 140.914 102.654) 
                         (list 140.973 102.663) 
                         (list 140.981 102.657) 
                         (list 140.998 102.66) 
                         "c"
         )
        (command "pline" (list 140.99 102.82) "w" 0 0 
                         (list 140.973 102.815) 
                         (list 140.969 102.806) 
                         (list 140.912 102.788) 
                         (list 140.909 102.798) 
                         (list 140.9 102.78) 
                         (list 140.918 102.771) 
                         (list 140.914 102.781) 
                         (list 140.971 102.799) 
                         (list 140.98 102.795) 
                         (list 140.996 102.8) 
                         "c"
         )
        (command "pline" (list 140.983 102.959) "w" 0 0 
                         (list 140.967 102.951) 
                         (list 140.964 102.941) 
                         (list 140.911 102.914) 
                         (list 140.906 102.924) 
                         (list 140.9 102.905) 
                         (list 140.919 102.899) 
                         (list 140.914 102.908) 
                         (list 140.967 102.935) 
                         (list 140.976 102.932) 
                         (list 140.992 102.94) 
                         "c"
         )
        (command "pline" (list 140.962 103.107) "w" 0 0 
                         (list 140.949 103.094) 
                         (list 140.949 103.084) 
                         (list 140.907 103.042) 
                         (list 140.9 103.05) 
                         (list 140.9 103.03) 
                         (list 140.92 103.03) 
                         (list 140.912 103.037) 
                         (list 140.954 103.079) 
                         (list 140.964 103.079) 
                         (list 140.977 103.092) 
                         "c"
         )
        (command "pline" (list 140.81 103.122) "w" 0 0 
                         (list 140.802 103.106) 
                         (list 140.805 103.097) 
                         (list 140.778 103.044) 
                         (list 140.769 103.049) 
                         (list 140.775 103.03) 
                         (list 140.794 103.036) 
                         (list 140.784 103.041) 
                         (list 140.811 103.094) 
                         (list 140.821 103.097) 
                         (list 140.829 103.113) 
                         "c"
         )
        (command "pline" (list 140.67 103.126) "w" 0 0 
                         (list 140.665 103.11) 
                         (list 140.669 103.101) 
                         (list 140.651 103.044) 
                         (list 140.641 103.048) 
                         (list 140.65 103.03) 
                         (list 140.668 103.039) 
                         (list 140.658 103.042) 
                         (list 140.676 103.099) 
                         (list 140.685 103.103) 
                         (list 140.69 103.12) 
                         "c"
         )
        (command "pline" (list 140.574 102.715) "w" 0 0 
                         (list 140.564 102.706) 
                         (list 140.564 102.698) 
                         (list 140.531 102.665) 
                         (list 140.525 102.671) 
                         (list 140.525 102.655) 
                         (list 140.541 102.655) 
                         (list 140.535 102.661) 
                         (list 140.568 102.694) 
                         (list 140.576 102.694) 
                         (list 140.585 102.704) 
                         "c"
         )
        (command "pline" (list 140.734 102.539) "w" 0 0 
                         (list 140.719 102.539) 
                         (list 140.713 102.533) 
                         (list 140.662 102.533) 
                         (list 140.662 102.542) 
                         (list 140.65 102.53) 
                         (list 140.662 102.518) 
                         (list 140.662 102.527) 
                         (list 140.713 102.527) 
                         (list 140.719 102.521) 
                         (list 140.734 102.521) 
                         "c"
         )
        (command "pline" (list 140.721 102.701) "w" 0 0 
                         (list 140.707 102.694) 
                         (list 140.705 102.686) 
                         (list 140.659 102.663) 
                         (list 140.655 102.671) 
                         (list 140.65 102.655) 
                         (list 140.666 102.65) 
                         (list 140.662 102.658) 
                         (list 140.707 102.681) 
                         (list 140.716 102.678) 
                         (list 140.729 102.685) 
                         "c"
         )
        (command "pline" (list 140.703 102.846) "w" 0 0 
                         (list 140.692 102.835) 
                         (list 140.692 102.827) 
                         (list 140.656 102.791) 
                         (list 140.65 102.797) 
                         (list 140.65 102.78) 
                         (list 140.667 102.78) 
                         (list 140.661 102.786) 
                         (list 140.697 102.822) 
                         (list 140.705 102.822) 
                         (list 140.716 102.833) 
                         "c"
         )
        (command "pline" (list 140.555 102.859) "w" 0 0 
                         (list 140.548 102.846) 
                         (list 140.551 102.837) 
                         (list 140.528 102.792) 
                         (list 140.52 102.796) 
                         (list 140.525 102.78) 
                         (list 140.541 102.785) 
                         (list 140.533 102.789) 
                         (list 140.556 102.835) 
                         (list 140.564 102.837) 
                         (list 140.571 102.851) 
                         "c"
         )
        (command "pline" (list 140.866 102.54) "w" 0 0 
                         (list 140.85 102.54) 
                         (list 140.843 102.533) 
                         (list 140.788 102.533) 
                         (list 140.788 102.543) 
                         (list 140.775 102.53) 
                         (list 140.788 102.517) 
                         (list 140.788 102.527) 
                         (list 140.843 102.527) 
                         (list 140.85 102.52) 
                         (list 140.866 102.52) 
                         "c"
         )
        (command "pline" (list 140.859 102.692) "w" 0 0 
                         (list 140.843 102.687) 
                         (list 140.839 102.679) 
                         (list 140.786 102.662) 
                         (list 140.783 102.671) 
                         (list 140.775 102.655) 
                         (list 140.791 102.647) 
                         (list 140.788 102.656) 
                         (list 140.841 102.673) 
                         (list 140.849 102.669) 
                         (list 140.865 102.674) 
                         "c"
         )
        (command "pline" (list 140.843 102.841) "w" 0 0 
                         (list 140.83 102.832) 
                         (list 140.828 102.823) 
                         (list 140.784 102.79) 
                         (list 140.778 102.798) 
                         (list 140.775 102.78) 
                         (list 140.793 102.777) 
                         (list 140.787 102.785) 
                         (list 140.832 102.817) 
                         (list 140.841 102.816) 
                         (list 140.854 102.826) 
                         "c"
         )
        (command "pline" (list 140.832 102.976) "w" 0 0 
                         (list 140.821 102.965) 
                         (list 140.821 102.956) 
                         (list 140.782 102.916) 
                         (list 140.775 102.923) 
                         (list 140.775 102.905) 
                         (list 140.793 102.905) 
                         (list 140.786 102.912) 
                         (list 140.826 102.951) 
                         (list 140.835 102.951) 
                         (list 140.846 102.962) 
                         "c"
         )
        (command "pline" (list 140.696 102.984) "w" 0 0 
                         (list 140.686 102.971) 
                         (list 140.687 102.962) 
                         (list 140.655 102.917) 
                         (list 140.647 102.923) 
                         (list 140.65 102.905) 
                         (list 140.668 102.908) 
                         (list 140.66 102.914) 
                         (list 140.693 102.958) 
                         (list 140.702 102.96) 
                         (list 140.711 102.973) 
                         "c"
         )
        (command "pline" (list 140.544 102.995) "w" 0 0 
                         (list 140.539 102.979) 
                         (list 140.543 102.971) 
                         (list 140.526 102.918) 
                         (list 140.517 102.921) 
                         (list 140.525 102.905) 
                         (list 140.541 102.913) 
                         (list 140.532 102.916) 
                         (list 140.549 102.969) 
                         (list 140.557 102.973) 
                         (list 140.562 102.989) 
                         "c"
         )
        (command "pline" (list 140.602 102.538) "w" 0 0 
                         (list 140.588 102.538) 
                         (list 140.583 102.533) 
                         (list 140.536 102.533) 
                         (list 140.536 102.541) 
                         (list 140.525 102.53) 
                         (list 140.536 102.519) 
                         (list 140.536 102.527) 
                         (list 140.583 102.527) 
                         (list 140.588 102.522) 
                         (list 140.602 102.522) 
                         "c"
         )
        (command "pline" (list 140.48 102.537) "w" 0 0 
                         (list 140.468 102.537) 
                         (list 140.463 102.533) 
                         (list 140.42 102.533) 
                         (list 140.42 102.54) 
                         (list 140.41 102.53) 
                         (list 140.42 102.52) 
                         (list 140.42 102.528) 
                         (list 140.463 102.528) 
                         (list 140.468 102.523) 
                         (list 140.48 102.523) 
                         "c"
         )
        (command "pline" (list 140.408 102.45) "w" 0 0 
                         (list 140.408 102.463) 
                         (list 140.403 102.468) 
                         (list 140.403 102.51) 
                         (list 140.41 102.51) 
                         (list 140.4 102.52) 
                         (list 140.39 102.51) 
                         (list 140.398 102.51) 
                         (list 140.398 102.468) 
                         (list 140.393 102.463) 
                         (list 140.393 102.45) 
                         "c"
         )
        (command "pline" (list 140.32 102.523) "w" 0 0 
                         (list 140.333 102.523) 
                         (list 140.338 102.528) 
                         (list 140.38 102.528) 
                         (list 140.38 102.52) 
                         (list 140.39 102.53) 
                         (list 140.38 102.54) 
                         (list 140.38 102.533) 
                         (list 140.338 102.533) 
                         (list 140.333 102.537) 
                         (list 140.32 102.537) 
                         "c"
         )
        (command "pline" (list 140.393 102.61) "w" 0 0 
                         (list 140.393 102.598) 
                         (list 140.398 102.593) 
                         (list 140.398 102.55) 
                         (list 140.39 102.55) 
                         (list 140.4 102.54) 
                         (list 140.41 102.55) 
                         (list 140.403 102.55) 
                         (list 140.403 102.593) 
                         (list 140.408 102.598) 
                         (list 140.408 102.61) 
                         "c"
         )
        (command "pline" (list 12.13 103.128) "w" 0 0 
                         (list 12.1272 103.111) 
                         (list 12.133 103.103) 
                         (list 12.1237 103.044) 
                         (list 12.1134 103.046) 
                         (list 12.125 103.03) 
                         (list 12.141 103.042) 
                         (list 12.1306 103.043) 
                         (list 12.14 103.102) 
                         (list 12.148 103.108) 
                         (list 12.1507 103.125) 
                         "c"
         )
        (command "pline" (list 12.73 102.541) "w" 0 0 
                         (list 12.7113 102.541) 
                         (list 12.7037 102.534) 
                         (list 12.64 102.534) 
                         (list 12.64 102.545) 
                         (list 12.625 102.53) 
                         (list 12.64 102.515) 
                         (list 12.64 102.526) 
                         (list 12.7037 102.526) 
                         (list 12.7113 102.519) 
                         (list 12.73 102.519) 
                         "c"
         )
        (command "pline" (list 12.7269 102.683) "w" 0 0 
                         (list 12.7084 102.68) 
                         (list 12.7022 102.671) 
                         (list 12.6392 102.661) 
                         (list 12.6375 102.672) 
                         (list 12.625 102.655) 
                         (list 12.6422 102.643) 
                         (list 12.6404 102.654) 
                         (list 12.7034 102.664) 
                         (list 12.7119 102.657) 
                         (list 12.7305 102.66) 
                         "c"
         )
        (command "pline" (list 12.7214 102.823) "w" 0 0 
                         (list 12.7036 102.817) 
                         (list 12.6987 102.808) 
                         (list 12.6381 102.788) 
                         (list 12.6346 102.799) 
                         (list 12.625 102.78) 
                         (list 12.6439 102.77) 
                         (list 12.6404 102.781) 
                         (list 12.7011 102.801) 
                         (list 12.7105 102.796) 
                         (list 12.7283 102.802) 
                         "c"
         )
        (command "pline" (list 12.7134 102.963) "w" 0 0 
                         (list 12.6967 102.954) 
                         (list 12.6935 102.944) 
                         (list 12.6367 102.915) 
                         (list 12.6316 102.925) 
                         (list 12.625 102.905) 
                         (list 12.6452 102.898) 
                         (list 12.6401 102.908) 
                         (list 12.6969 102.937) 
                         (list 12.707 102.934) 
                         (list 12.7237 102.943) 
                         "c"
         )
        (command "pline" (list 12.7033 103.101) "w" 0 0 
                         (list 12.6882 103.09) 
                         (list 12.6865 103.079) 
                         (list 12.6349 103.042) 
                         (list 12.6283 103.051) 
                         (list 12.625 103.03) 
                         (list 12.646 103.027) 
                         (list 12.6393 103.036) 
                         (list 12.6909 103.073) 
                         (list 12.7014 103.072) 
                         (list 12.7166 103.083) 
                         "c"
         )
        (command "pline" (list 12.6913 103.237) "w" 0 0 
                         (list 12.678 103.224) 
                         (list 12.678 103.213) 
                         (list 12.633 103.168) 
                         (list 12.625 103.176) 
                         (list 12.625 103.155) 
                         (list 12.6462 103.155) 
                         (list 12.6383 103.163) 
                         (list 12.6833 103.208) 
                         (list 12.6939 103.208) 
                         (list 12.7072 103.221) 
                         "c"
         )
        (command "pline" (list 12.5526 103.247) "w" 0 0 
                         (list 12.5416 103.231) 
                         (list 12.5433 103.221) 
                         (list 12.5058 103.169) 
                         (list 12.4967 103.176) 
                         (list 12.5 103.155) 
                         (list 12.521 103.158) 
                         (list 12.5119 103.165) 
                         (list 12.5493 103.217) 
                         (list 12.5598 103.218) 
                         (list 12.5708 103.233) 
                         "c"
         )
        (command "pline" (list 12.4126 103.254) "w" 0 0 
                         (list 12.4041 103.237) 
                         (list 12.4074 103.227) 
                         (list 12.3785 103.17) 
                         (list 12.3684 103.175) 
                         (list 12.375 103.155) 
                         (list 12.3952 103.162) 
                         (list 12.3852 103.167) 
                         (list 12.4141 103.223) 
                         (list 12.4242 103.227) 
                         (list 12.4327 103.243) 
                         "c"
         )
        (command "pline" (list 12.2717 103.258) "w" 0 0 
                         (list 12.266 103.241) 
                         (list 12.2708 103.231) 
                         (list 12.2511 103.17) 
                         (list 12.2404 103.174) 
                         (list 12.25 103.155) 
                         (list 12.2689 103.165) 
                         (list 12.2582 103.168) 
                         (list 12.2779 103.229) 
                         (list 12.2874 103.234) 
                         (list 12.2931 103.251) 
                         "c"
         )
        (command "pline" (list 12.1303 103.26) "w" 0 0 
                         (list 12.1274 103.242) 
                         (list 12.1336 103.233) 
                         (list 12.1236 103.17) 
                         (list 12.1125 103.172) 
                         (list 12.125 103.155) 
                         (list 12.1422 103.167) 
                         (list 12.1311 103.169) 
                         (list 12.141 103.232) 
                         (list 12.1496 103.238) 
                         (list 12.1525 103.257) 
                         "c"
         )
        (command "pline" (list 11.5354 102.674) "w" 0 0 
                         (list 11.5509 102.669) 
                         (list 11.5591 102.673) 
                         (list 11.6116 102.656) 
                         (list 11.6086 102.647) 
                         (list 11.625 102.655) 
                         (list 11.6167 102.671) 
                         (list 11.6136 102.662) 
                         (list 11.5611 102.679) 
                         (list 11.5569 102.687) 
                         (list 11.5415 102.692) 
                         "c"
         )
        (command "pline" (list 11.4016 102.66) "w" 0 0 
                         (list 11.4188 102.657) 
                         (list 11.4269 102.663) 
                         (list 11.4856 102.654) 
                         (list 11.484 102.643) 
                         (list 11.5 102.655) 
                         (list 11.4884 102.671) 
                         (list 11.4867 102.661) 
                         (list 11.428 102.67) 
                         (list 11.4221 102.678) 
                         (list 11.4048 102.681) 
                         "c"
         )
        (command "pline" (list 11.2695 102.66) "w" 0 0 
                         (list 11.2881 102.657) 
                         (list 11.2966 102.664) 
                         (list 11.3596 102.654) 
                         (list 11.3578 102.643) 
                         (list 11.375 102.655) 
                         (list 11.3625 102.672) 
                         (list 11.3608 102.661) 
                         (list 11.2978 102.671) 
                         (list 11.2916 102.68) 
                         (list 11.2731 102.683) 
                         "c"
         )
        (command "pline" (list 11.9918 102.732) "w" 0 0 
                         (list 11.9918 102.718) 
                         (list 11.9972 102.713) 
                         (list 11.9972 102.666) 
                         (list 11.989 102.666) 
                         (list 12.0 102.655) 
                         (list 12.011 102.666) 
                         (list 12.0028 102.666) 
                         (list 12.0028 102.713) 
                         (list 12.0083 102.718) 
                         (list 12.0083 102.732) 
                         "c"
         )
        (command "pline" (list 11.8147 102.704) "w" 0 0 
                         (list 11.8244 102.694) 
                         (list 11.8322 102.694) 
                         (list 11.8653 102.661) 
                         (list 11.8594 102.655) 
                         (list 11.875 102.655) 
                         (list 11.875 102.671) 
                         (list 11.8692 102.665) 
                         (list 11.8361 102.698) 
                         (list 11.8361 102.706) 
                         (list 11.8264 102.715) 
                         "c"
         )
        (command "pline" (list 11.6711 102.685) "w" 0 0 
                         (list 11.6844 102.678) 
                         (list 11.6925 102.681) 
                         (list 11.7379 102.658) 
                         (list 11.7339 102.65) 
                         (list 11.75 102.655) 
                         (list 11.7448 102.671) 
                         (list 11.7407 102.663) 
                         (list 11.6952 102.686) 
                         (list 11.6926 102.694) 
                         (list 11.6792 102.701) 
                         "c"
         )
        (command "pline" (list 11.991 102.864) "w" 0 0 
                         (list 11.991 102.849) 
                         (list 11.997 102.843) 
                         (list 11.997 102.792) 
                         (list 11.988 102.792) 
                         (list 12.0 102.78) 
                         (list 12.012 102.792) 
                         (list 12.003 102.792) 
                         (list 12.003 102.843) 
                         (list 12.009 102.849) 
                         (list 12.009 102.864) 
                         "c"
         )
        (command "pline" (list 11.8288 102.851) "w" 0 0 
                         (list 11.8357 102.837) 
                         (list 11.8437 102.835) 
                         (list 11.8669 102.789) 
                         (list 11.8589 102.785) 
                         (list 11.875 102.78) 
                         (list 11.8802 102.796) 
                         (list 11.8722 102.792) 
                         (list 11.8491 102.837) 
                         (list 11.8517 102.846) 
                         (list 11.8449 102.859) 
                         "c"
         )
        (command "pline" (list 11.6842 102.833) "w" 0 0 
                         (list 11.6948 102.822) 
                         (list 11.7033 102.822) 
                         (list 11.7394 102.786) 
                         (list 11.733 102.78) 
                         (list 11.75 102.78) 
                         (list 11.75 102.797) 
                         (list 11.7436 102.791) 
                         (list 11.7076 102.827) 
                         (list 11.7076 102.835) 
                         (list 11.697 102.846) 
                         "c"
         )
        (command "pline" (list 11.5456 102.826) "w" 0 0 
                         (list 11.5588 102.816) 
                         (list 11.5679 102.817) 
                         (list 11.6126 102.785) 
                         (list 11.6068 102.777) 
                         (list 11.625 102.78) 
                         (list 11.6221 102.798) 
                         (list 11.6164 102.79) 
                         (list 11.5717 102.823) 
                         (list 11.5703 102.832) 
                         (list 11.5571 102.841) 
                         "c"
         )
        (command "pline" (list 11.4036 102.8) "w" 0 0 
                         (list 11.4202 102.795) 
                         (list 11.429 102.799) 
                         (list 11.4856 102.781) 
                         (list 11.4824 102.771) 
                         (list 11.5 102.78) 
                         (list 11.491 102.798) 
                         (list 11.4878 102.788) 
                         (list 11.4312 102.806) 
                         (list 11.4267 102.815) 
                         (list 11.41 102.82) 
                         "c"
         )
        (command "pline" (list 11.2717 102.802) "w" 0 0 
                         (list 11.2895 102.796) 
                         (list 11.2989 102.801) 
                         (list 11.3596 102.781) 
                         (list 11.3561 102.77) 
                         (list 11.375 102.78) 
                         (list 11.3654 102.799) 
                         (list 11.3619 102.788) 
                         (list 11.3013 102.808) 
                         (list 11.2964 102.817) 
                         (list 11.2786 102.823) 
                         "c"
         )
        (command "pline" (list 11.9903 102.996) "w" 0 0 
                         (list 11.9903 102.98) 
                         (list 11.9968 102.973) 
                         (list 11.9968 102.918) 
                         (list 11.987 102.918) 
                         (list 12.0 102.905) 
                         (list 12.013 102.918) 
                         (list 12.0033 102.918) 
                         (list 12.0033 102.973) 
                         (list 12.0098 102.98) 
                         (list 12.0098 102.996) 
                         "c"
         )
        (command "pline" (list 11.8376 102.989) "w" 0 0 
                         (list 11.8426 102.973) 
                         (list 11.8508 102.969) 
                         (list 11.8679 102.916) 
                         (list 11.8586 102.913) 
                         (list 11.875 102.905) 
                         (list 11.8833 102.921) 
                         (list 11.8741 102.918) 
                         (list 11.857 102.971) 
                         (list 11.8612 102.979) 
                         (list 11.8562 102.995) 
                         "c"
         )
        (command "pline" (list 11.6886 102.973) "w" 0 0 
                         (list 11.6982 102.96) 
                         (list 11.7073 102.958) 
                         (list 11.7397 102.914) 
                         (list 11.7318 102.908) 
                         (list 11.75 102.905) 
                         (list 11.7529 102.923) 
                         (list 11.745 102.917) 
                         (list 11.7125 102.962) 
                         (list 11.714 102.971) 
                         (list 11.7044 102.984) 
                         "c"
         )
        (command "pline" (list 11.5538 102.962) "w" 0 0 
                         (list 11.5652 102.951) 
                         (list 11.5744 102.951) 
                         (list 11.6135 102.912) 
                         (list 11.6066 102.905) 
                         (list 11.625 102.905) 
                         (list 11.625 102.923) 
                         (list 11.6181 102.916) 
                         (list 11.579 102.956) 
                         (list 11.579 102.965) 
                         (list 11.5675 102.976) 
                         "c"
         )
        (command "pline" (list 11.4079 102.94) "w" 0 0 
                         (list 11.4235 102.932) 
                         (list 11.4329 102.935) 
                         (list 11.4859 102.908) 
                         (list 11.4812 102.899) 
                         (list 11.5 102.905) 
                         (list 11.4939 102.924) 
                         (list 11.4891 102.914) 
                         (list 11.4361 102.941) 
                         (list 11.433 102.951) 
                         (list 11.4174 102.959) 
                         "c"
         )
        (command "pline" (list 11.2763 102.943) "w" 0 0 
                         (list 11.293 102.934) 
                         (list 11.3031 102.937) 
                         (list 11.3599 102.908) 
                         (list 11.3548 102.898) 
                         (list 11.375 102.905) 
                         (list 11.3684 102.925) 
                         (list 11.3633 102.915) 
                         (list 11.3065 102.944) 
                         (list 11.3033 102.954) 
                         (list 11.2866 102.963) 
                         "c"
         )
        (command "pline" (list 11.4233 103.092) "w" 0 0 
                         (list 11.4357 103.079) 
                         (list 11.4456 103.079) 
                         (list 11.4876 103.037) 
                         (list 11.4802 103.03) 
                         (list 11.5 103.03) 
                         (list 11.5 103.05) 
                         (list 11.4926 103.042) 
                         (list 11.4505 103.084) 
                         (list 11.4505 103.094) 
                         (list 11.4381 103.107) 
                         "c"
         )
        (command "pline" (list 11.2834 103.083) "w" 0 0 
                         (list 11.2986 103.072) 
                         (list 11.3091 103.073) 
                         (list 11.3607 103.036) 
                         (list 11.354 103.027) 
                         (list 11.375 103.03) 
                         (list 11.3717 103.051) 
                         (list 11.3651 103.042) 
                         (list 11.3135 103.079) 
                         (list 11.3118 103.09) 
                         (list 11.2967 103.101) 
                         "c"
         )
        (command "pline" (list 11.9895 103.128) "w" 0 0 
                         (list 11.9895 103.111) 
                         (list 11.9965 103.104) 
                         (list 11.9965 103.044) 
                         (list 11.986 103.044) 
                         (list 12.0 103.03) 
                         (list 12.014 103.044) 
                         (list 12.0035 103.044) 
                         (list 12.0035 103.104) 
                         (list 12.0105 103.111) 
                         (list 12.0105 103.128) 
                         "c"
         )
        (command "pline" (list 11.8493 103.125) "w" 0 0 
                         (list 11.852 103.108) 
                         (list 11.86 103.102) 
                         (list 11.8694 103.043) 
                         (list 11.859 103.042) 
                         (list 11.875 103.03) 
                         (list 11.8866 103.046) 
                         (list 11.8763 103.044) 
                         (list 11.867 103.103) 
                         (list 11.8728 103.111) 
                         (list 11.87 103.128) 
                         "c"
         )
        (command "pline" (list 11.7097 103.12) "w" 0 0 
                         (list 11.7151 103.103) 
                         (list 11.724 103.099) 
                         (list 11.7423 103.042) 
                         (list 11.7324 103.039) 
                         (list 11.75 103.03) 
                         (list 11.759 103.048) 
                         (list 11.749 103.044) 
                         (list 11.7306 103.101) 
                         (list 11.7351 103.11) 
                         (list 11.7297 103.126) 
                         "c"
         )
        (command "pline" (list 11.5712 103.113) "w" 0 0 
                         (list 11.5791 103.097) 
                         (list 11.5885 103.094) 
                         (list 11.6155 103.041) 
                         (list 11.6062 103.036) 
                         (list 11.625 103.03) 
                         (list 11.6311 103.049) 
                         (list 11.6218 103.044) 
                         (list 11.5947 103.097) 
                         (list 11.5978 103.106) 
                         (list 11.5899 103.122) 
                         "c"
         )
        (command "pline" (list 11.9888 103.26) "w" 0 0 
                         (list 11.9888 103.241) 
                         (list 11.9963 103.234) 
                         (list 11.9963 103.17) 
                         (list 11.985 103.17) 
                         (list 12.0 103.155) 
                         (list 12.015 103.17) 
                         (list 12.0038 103.17) 
                         (list 12.0038 103.234) 
                         (list 12.0113 103.241) 
                         (list 12.0113 103.26) 
                         "c"
         )
        (command "pline" (list 11.8475 103.257) "w" 0 0 
                         (list 11.8504 103.238) 
                         (list 11.859 103.232) 
                         (list 11.869 103.169) 
                         (list 11.8578 103.167) 
                         (list 11.875 103.155) 
                         (list 11.8875 103.172) 
                         (list 11.8764 103.17) 
                         (list 11.8664 103.233) 
                         (list 11.8726 103.242) 
                         (list 11.8697 103.26) 
                         "c"
         )
        (command "pline" (list 11.7069 103.251) "w" 0 0 
                         (list 11.7126 103.234) 
                         (list 11.7221 103.229) 
                         (list 11.7418 103.168) 
                         (list 11.7311 103.165) 
                         (list 11.75 103.155) 
                         (list 11.7596 103.174) 
                         (list 11.7489 103.17) 
                         (list 11.7292 103.231) 
                         (list 11.734 103.241) 
                         (list 11.7283 103.258) 
                         "c"
         )
        (command "pline" (list 11.5673 103.243) "w" 0 0 
                         (list 11.5758 103.227) 
                         (list 11.5859 103.223) 
                         (list 11.6148 103.167) 
                         (list 11.6048 103.162) 
                         (list 11.625 103.155) 
                         (list 11.6316 103.175) 
                         (list 11.6215 103.17) 
                         (list 11.5926 103.227) 
                         (list 11.5959 103.237) 
                         (list 11.5874 103.254) 
                         "c"
         )
        (command "pline" (list 11.4292 103.233) "w" 0 0 
                         (list 11.4402 103.218) 
                         (list 11.4507 103.217) 
                         (list 11.4881 103.165) 
                         (list 11.479 103.158) 
                         (list 11.5 103.155) 
                         (list 11.5033 103.176) 
                         (list 11.4942 103.169) 
                         (list 11.4567 103.221) 
                         (list 11.4584 103.231) 
                         (list 11.4474 103.247) 
                         "c"
         )
        (command "pline" (list 11.2928 103.221) "w" 0 0 
                         (list 11.3061 103.208) 
                         (list 11.3167 103.208) 
                         (list 11.3617 103.163) 
                         (list 11.3538 103.155) 
                         (list 11.375 103.155) 
                         (list 11.375 103.176) 
                         (list 11.367 103.168) 
                         (list 11.322 103.213) 
                         (list 11.322 103.224) 
                         (list 11.3087 103.237) 
                         "c"
         )
        (command "pline" (list 11.8562 102.065) "w" 0 0 
                         (list 11.8612 102.081) 
                         (list 11.857 102.089) 
                         (list 11.8741 102.142) 
                         (list 11.8833 102.139) 
                         (list 11.875 102.155) 
                         (list 11.8586 102.147) 
                         (list 11.8679 102.144) 
                         (list 11.8508 102.091) 
                         (list 11.8426 102.087) 
                         (list 11.8376 102.071) 
                         "c"
         )
        (command "pline" (list 11.87 101.932) "w" 0 0 
                         (list 11.8728 101.949) 
                         (list 11.867 101.957) 
                         (list 11.8763 102.016) 
                         (list 11.8866 102.014) 
                         (list 11.875 102.03) 
                         (list 11.859 102.018) 
                         (list 11.8694 102.017) 
                         (list 11.86 101.958) 
                         (list 11.852 101.952) 
                         (list 11.8493 101.935) 
                         "c"
         )
        (command "pline" (list 11.8697 101.8) "w" 0 0 
                         (list 11.8726 101.818) 
                         (list 11.8664 101.827) 
                         (list 11.8764 101.89) 
                         (list 11.8875 101.888) 
                         (list 11.875 101.905) 
                         (list 11.8578 101.893) 
                         (list 11.869 101.891) 
                         (list 11.859 101.828) 
                         (list 11.8504 101.822) 
                         (list 11.8475 101.803) 
                         "c"
         )
        (command "pline" (list 11.798 102.522) "w" 0 0 
                         (list 11.8118 102.522) 
                         (list 11.8173 102.527) 
                         (list 11.864 102.527) 
                         (list 11.864 102.519) 
                         (list 11.875 102.53) 
                         (list 11.864 102.541) 
                         (list 11.864 102.533) 
                         (list 11.8173 102.533) 
                         (list 11.8118 102.538) 
                         (list 11.798 102.538) 
                         "c"
         )
        (command "pline" (list 11.8264 102.345) "w" 0 0 
                         (list 11.8361 102.354) 
                         (list 11.8361 102.362) 
                         (list 11.8692 102.395) 
                         (list 11.875 102.389) 
                         (list 11.875 102.405) 
                         (list 11.8594 102.405) 
                         (list 11.8653 102.399) 
                         (list 11.8322 102.366) 
                         (list 11.8244 102.366) 
                         (list 11.8147 102.356) 
                         "c"
         )
        (command "pline" (list 11.8449 102.201) "w" 0 0 
                         (list 11.8517 102.214) 
                         (list 11.8491 102.223) 
                         (list 11.8722 102.268) 
                         (list 11.8802 102.264) 
                         (list 11.875 102.28) 
                         (list 11.8589 102.275) 
                         (list 11.8669 102.271) 
                         (list 11.8437 102.225) 
                         (list 11.8357 102.223) 
                         (list 11.8288 102.209) 
                         "c"
         )
        (command "pline" (list 11.666 102.521) "w" 0 0 
                         (list 11.681 102.521) 
                         (list 11.687 102.527) 
                         (list 11.738 102.527) 
                         (list 11.738 102.518) 
                         (list 11.75 102.53) 
                         (list 11.738 102.542) 
                         (list 11.738 102.533) 
                         (list 11.687 102.533) 
                         (list 11.681 102.539) 
                         (list 11.666 102.539) 
                         "c"
         )
        (command "pline" (list 11.6792 102.359) "w" 0 0 
                         (list 11.6926 102.366) 
                         (list 11.6952 102.374) 
                         (list 11.7407 102.397) 
                         (list 11.7448 102.389) 
                         (list 11.75 102.405) 
                         (list 11.7339 102.41) 
                         (list 11.7379 102.402) 
                         (list 11.6925 102.379) 
                         (list 11.6844 102.382) 
                         (list 11.6711 102.375) 
                         "c"
         )
        (command "pline" (list 11.697 102.214) "w" 0 0 
                         (list 11.7076 102.225) 
                         (list 11.7076 102.233) 
                         (list 11.7436 102.269) 
                         (list 11.75 102.263) 
                         (list 11.75 102.28) 
                         (list 11.733 102.28) 
                         (list 11.7394 102.274) 
                         (list 11.7033 102.238) 
                         (list 11.6948 102.238) 
                         (list 11.6842 102.227) 
                         "c"
         )
        (command "pline" (list 11.7044 102.076) "w" 0 0 
                         (list 11.714 102.089) 
                         (list 11.7125 102.098) 
                         (list 11.745 102.143) 
                         (list 11.7529 102.137) 
                         (list 11.75 102.155) 
                         (list 11.7318 102.152) 
                         (list 11.7397 102.146) 
                         (list 11.7073 102.102) 
                         (list 11.6982 102.1) 
                         (list 11.6886 102.087) 
                         "c"
         )
        (command "pline" (list 11.7297 101.934) "w" 0 0 
                         (list 11.7351 101.95) 
                         (list 11.7306 101.959) 
                         (list 11.749 102.016) 
                         (list 11.759 102.012) 
                         (list 11.75 102.03) 
                         (list 11.7324 102.021) 
                         (list 11.7423 102.018) 
                         (list 11.724 101.961) 
                         (list 11.7151 101.957) 
                         (list 11.7097 101.94) 
                         "c"
         )
        (command "pline" (list 11.7283 101.802) "w" 0 0 
                         (list 11.734 101.819) 
                         (list 11.7292 101.829) 
                         (list 11.7489 101.89) 
                         (list 11.7596 101.886) 
                         (list 11.75 101.905) 
                         (list 11.7311 101.895) 
                         (list 11.7418 101.892) 
                         (list 11.7221 101.831) 
                         (list 11.7126 101.826) 
                         (list 11.7069 101.809) 
                         "c"
         )
        (command "pline" (list 11.534 102.52) "w" 0 0 
                         (list 11.5503 102.52) 
                         (list 11.5567 102.527) 
                         (list 11.612 102.527) 
                         (list 11.612 102.517) 
                         (list 11.625 102.53) 
                         (list 11.612 102.543) 
                         (list 11.612 102.533) 
                         (list 11.5567 102.533) 
                         (list 11.5503 102.54) 
                         (list 11.534 102.54) 
                         "c"
         )
        (command "pline" (list 11.5415 102.368) "w" 0 0 
                         (list 11.5569 102.373) 
                         (list 11.5611 102.381) 
                         (list 11.6136 102.398) 
                         (list 11.6167 102.389) 
                         (list 11.625 102.405) 
                         (list 11.6086 102.413) 
                         (list 11.6116 102.404) 
                         (list 11.5591 102.387) 
                         (list 11.5509 102.391) 
                         (list 11.5354 102.386) 
                         "c"
         )
        (command "pline" (list 11.5571 102.219) "w" 0 0 
                         (list 11.5703 102.228) 
                         (list 11.5717 102.237) 
                         (list 11.6164 102.27) 
                         (list 11.6221 102.262) 
                         (list 11.625 102.28) 
                         (list 11.6068 102.283) 
                         (list 11.6126 102.275) 
                         (list 11.5679 102.243) 
                         (list 11.5588 102.244) 
                         (list 11.5456 102.234) 
                         "c"
         )
        (command "pline" (list 11.5675 102.084) "w" 0 0 
                         (list 11.579 102.095) 
                         (list 11.579 102.104) 
                         (list 11.6181 102.144) 
                         (list 11.625 102.137) 
                         (list 11.625 102.155) 
                         (list 11.6066 102.155) 
                         (list 11.6135 102.148) 
                         (list 11.5744 102.109) 
                         (list 11.5652 102.109) 
                         (list 11.5538 102.098) 
                         "c"
         )
        (command "pline" (list 11.5899 101.938) "w" 0 0 
                         (list 11.5978 101.954) 
                         (list 11.5947 101.963) 
                         (list 11.6218 102.016) 
                         (list 11.6311 102.011) 
                         (list 11.625 102.03) 
                         (list 11.6062 102.024) 
                         (list 11.6155 102.019) 
                         (list 11.5885 101.966) 
                         (list 11.5791 101.963) 
                         (list 11.5712 101.947) 
                         "c"
         )
        (command "pline" (list 11.5874 101.806) "w" 0 0 
                         (list 11.5959 101.823) 
                         (list 11.5926 101.833) 
                         (list 11.6215 101.89) 
                         (list 11.6316 101.885) 
                         (list 11.625 101.905) 
                         (list 11.6048 101.898) 
                         (list 11.6148 101.893) 
                         (list 11.5859 101.837) 
                         (list 11.5758 101.833) 
                         (list 11.5673 101.817) 
                         "c"
         )
        (command "pline" (list 11.4381 101.953) "w" 0 0 
                         (list 11.4505 101.966) 
                         (list 11.4505 101.976) 
                         (list 11.4926 102.018) 
                         (list 11.5 102.01) 
                         (list 11.5 102.03) 
                         (list 11.4802 102.03) 
                         (list 11.4876 102.023) 
                         (list 11.4456 101.981) 
                         (list 11.4357 101.981) 
                         (list 11.4233 101.968) 
                         "c"
         )
        (command "pline" (list 11.4474 101.813) "w" 0 0 
                         (list 11.4584 101.829) 
                         (list 11.4567 101.839) 
                         (list 11.4942 101.891) 
                         (list 11.5033 101.884) 
                         (list 11.5 101.905) 
                         (list 11.479 101.902) 
                         (list 11.4881 101.895) 
                         (list 11.4507 101.843) 
                         (list 11.4402 101.842) 
                         (list 11.4292 101.827) 
                         "c"
         )
        (command "pline" (list 11.402 102.52) "w" 0 0 
                         (list 11.4195 102.52) 
                         (list 11.4265 102.527) 
                         (list 11.486 102.527) 
                         (list 11.486 102.516) 
                         (list 11.5 102.53) 
                         (list 11.486 102.544) 
                         (list 11.486 102.534) 
                         (list 11.4265 102.534) 
                         (list 11.4195 102.54) 
                         (list 11.402 102.54) 
                         "c"
         )
        (command "pline" (list 11.4048 102.379) "w" 0 0 
                         (list 11.4221 102.382) 
                         (list 11.428 102.39) 
                         (list 11.4867 102.399) 
                         (list 11.4884 102.389) 
                         (list 11.5 102.405) 
                         (list 11.484 102.417) 
                         (list 11.4856 102.406) 
                         (list 11.4269 102.397) 
                         (list 11.4188 102.403) 
                         (list 11.4016 102.4) 
                         "c"
         )
        (command "pline" (list 11.41 102.24) "w" 0 0 
                         (list 11.4267 102.245) 
                         (list 11.4312 102.254) 
                         (list 11.4878 102.272) 
                         (list 11.491 102.262) 
                         (list 11.5 102.28) 
                         (list 11.4824 102.289) 
                         (list 11.4856 102.279) 
                         (list 11.429 102.261) 
                         (list 11.4202 102.265) 
                         (list 11.4036 102.26) 
                         "c"
         )
        (command "pline" (list 11.4174 102.101) "w" 0 0 
                         (list 11.433 102.109) 
                         (list 11.4361 102.119) 
                         (list 11.4891 102.146) 
                         (list 11.4939 102.136) 
                         (list 11.5 102.155) 
                         (list 11.4812 102.161) 
                         (list 11.4859 102.152) 
                         (list 11.4329 102.125) 
                         (list 11.4235 102.128) 
                         (list 11.4079 102.12) 
                         "c"
         )
        (command "pline" (list 11.27 102.519) "w" 0 0 
                         (list 11.2888 102.519) 
                         (list 11.2963 102.526) 
                         (list 11.36 102.526) 
                         (list 11.36 102.515) 
                         (list 11.375 102.53) 
                         (list 11.36 102.545) 
                         (list 11.36 102.534) 
                         (list 11.2963 102.534) 
                         (list 11.2888 102.541) 
                         (list 11.27 102.541) 
                         "c"
         )
        (command "pline" (list 11.2731 102.377) "w" 0 0 
                         (list 11.2916 102.38) 
                         (list 11.2978 102.389) 
                         (list 11.3608 102.399) 
                         (list 11.3625 102.388) 
                         (list 11.375 102.405) 
                         (list 11.3578 102.417) 
                         (list 11.3596 102.406) 
                         (list 11.2966 102.396) 
                         (list 11.2881 102.403) 
                         (list 11.2695 102.4) 
                         "c"
         )
        (command "pline" (list 11.2786 102.237) "w" 0 0 
                         (list 11.2964 102.243) 
                         (list 11.3013 102.252) 
                         (list 11.3619 102.272) 
                         (list 11.3654 102.261) 
                         (list 11.375 102.28) 
                         (list 11.3561 102.29) 
                         (list 11.3596 102.279) 
                         (list 11.2989 102.259) 
                         (list 11.2895 102.264) 
                         (list 11.2717 102.258) 
                         "c"
         )
        (command "pline" (list 11.2866 102.097) "w" 0 0 
                         (list 11.3033 102.106) 
                         (list 11.3065 102.116) 
                         (list 11.3633 102.145) 
                         (list 11.3684 102.135) 
                         (list 11.375 102.155) 
                         (list 11.3548 102.162) 
                         (list 11.3599 102.152) 
                         (list 11.3031 102.123) 
                         (list 11.293 102.126) 
                         (list 11.2763 102.117) 
                         "c"
         )
        (command "pline" (list 11.2967 101.959) "w" 0 0 
                         (list 11.3118 101.97) 
                         (list 11.3135 101.981) 
                         (list 11.3651 102.018) 
                         (list 11.3717 102.009) 
                         (list 11.375 102.03) 
                         (list 11.354 102.033) 
                         (list 11.3607 102.024) 
                         (list 11.3091 101.987) 
                         (list 11.2986 101.988) 
                         (list 11.2834 101.977) 
                         "c"
         )
        (command "pline" (list 11.3087 101.823) "w" 0 0 
                         (list 11.322 101.836) 
                         (list 11.322 101.847) 
                         (list 11.367 101.892) 
                         (list 11.375 101.884) 
                         (list 11.375 101.905) 
                         (list 11.3538 101.905) 
                         (list 11.3617 101.897) 
                         (list 11.3167 101.852) 
                         (list 11.3061 101.852) 
                         (list 11.2928 101.839) 
                         "c"
         )
        (command "pline" (list 12.7072 101.839) "w" 0 0 
                         (list 12.6939 101.852) 
                         (list 12.6833 101.852) 
                         (list 12.6383 101.897) 
                         (list 12.6462 101.905) 
                         (list 12.625 101.905) 
                         (list 12.625 101.884) 
                         (list 12.633 101.892) 
                         (list 12.678 101.847) 
                         (list 12.678 101.836) 
                         (list 12.6913 101.823) 
                         "c"
         )
        (command "pline" (list 12.5708 101.827) "w" 0 0 
                         (list 12.5598 101.842) 
                         (list 12.5493 101.843) 
                         (list 12.5119 101.895) 
                         (list 12.521 101.902) 
                         (list 12.5 101.905) 
                         (list 12.4967 101.884) 
                         (list 12.5058 101.891) 
                         (list 12.5433 101.839) 
                         (list 12.5416 101.829) 
                         (list 12.5526 101.813) 
                         "c"
         )
        (command "pline" (list 12.4327 101.817) "w" 0 0 
                         (list 12.4242 101.833) 
                         (list 12.4141 101.837) 
                         (list 12.3852 101.893) 
                         (list 12.3952 101.898) 
                         (list 12.375 101.905) 
                         (list 12.3684 101.885) 
                         (list 12.3785 101.89) 
                         (list 12.4074 101.833) 
                         (list 12.4041 101.823) 
                         (list 12.4126 101.806) 
                         "c"
         )
        (command "pline" (list 12.2931 101.809) "w" 0 0 
                         (list 12.2874 101.826) 
                         (list 12.2779 101.831) 
                         (list 12.2582 101.892) 
                         (list 12.2689 101.895) 
                         (list 12.25 101.905) 
                         (list 12.2404 101.886) 
                         (list 12.2511 101.89) 
                         (list 12.2708 101.829) 
                         (list 12.266 101.819) 
                         (list 12.2717 101.802) 
                         "c"
         )
        (command "pline" (list 12.1525 101.803) "w" 0 0 
                         (list 12.1496 101.822) 
                         (list 12.141 101.828) 
                         (list 12.1311 101.891) 
                         (list 12.1422 101.893) 
                         (list 12.125 101.905) 
                         (list 12.1125 101.888) 
                         (list 12.1236 101.89) 
                         (list 12.1336 101.827) 
                         (list 12.1274 101.818) 
                         (list 12.1303 101.8) 
                         "c"
         )
        (command "pline" (list 12.0113 101.8) "w" 0 0 
                         (list 12.0113 101.819) 
                         (list 12.0038 101.826) 
                         (list 12.0038 101.89) 
                         (list 12.015 101.89) 
                         (list 12.0 101.905) 
                         (list 11.985 101.89) 
                         (list 11.9963 101.89) 
                         (list 11.9963 101.826) 
                         (list 11.9888 101.819) 
                         (list 11.9888 101.8) 
                         "c"
         )
        (command "pline" (list 12.7166 101.977) "w" 0 0 
                         (list 12.7014 101.988) 
                         (list 12.6909 101.987) 
                         (list 12.6393 102.024) 
                         (list 12.646 102.033) 
                         (list 12.625 102.03) 
                         (list 12.6283 102.009) 
                         (list 12.6349 102.018) 
                         (list 12.6865 101.981) 
                         (list 12.6882 101.97) 
                         (list 12.7033 101.959) 
                         "c"
         )
        (command "pline" (list 12.5767 101.968) "w" 0 0 
                         (list 12.5643 101.981) 
                         (list 12.5544 101.981) 
                         (list 12.5124 102.023) 
                         (list 12.5198 102.03) 
                         (list 12.5 102.03) 
                         (list 12.5 102.01) 
                         (list 12.5074 102.018) 
                         (list 12.5495 101.976) 
                         (list 12.5495 101.966) 
                         (list 12.5619 101.953) 
                         "c"
         )
        (command "pline" (list 12.4288 101.947) "w" 0 0 
                         (list 12.4209 101.963) 
                         (list 12.4115 101.966) 
                         (list 12.3845 102.019) 
                         (list 12.3938 102.024) 
                         (list 12.375 102.03) 
                         (list 12.3689 102.011) 
                         (list 12.3782 102.016) 
                         (list 12.4053 101.963) 
                         (list 12.4022 101.954) 
                         (list 12.4101 101.938) 
                         "c"
         )
        (command "pline" (list 12.2903 101.94) "w" 0 0 
                         (list 12.2849 101.957) 
                         (list 12.276 101.961) 
                         (list 12.2577 102.018) 
                         (list 12.2676 102.021) 
                         (list 12.25 102.03) 
                         (list 12.241 102.012) 
                         (list 12.251 102.016) 
                         (list 12.2694 101.959) 
                         (list 12.2649 101.95) 
                         (list 12.2703 101.934) 
                         "c"
         )
        (command "pline" (list 12.1507 101.935) "w" 0 0 
                         (list 12.148 101.952) 
                         (list 12.14 101.958) 
                         (list 12.1306 102.017) 
                         (list 12.141 102.018) 
                         (list 12.125 102.03) 
                         (list 12.1134 102.014) 
                         (list 12.1237 102.016) 
                         (list 12.133 101.957) 
                         (list 12.1272 101.949) 
                         (list 12.13 101.932) 
                         "c"
         )
        (command "pline" (list 12.0105 101.932) "w" 0 0 
                         (list 12.0105 101.95) 
                         (list 12.0035 101.957) 
                         (list 12.0035 102.016) 
                         (list 12.014 102.016) 
                         (list 12.0 102.03) 
                         (list 11.986 102.016) 
                         (list 11.9965 102.016) 
                         (list 11.9965 101.957) 
                         (list 11.9895 101.95) 
                         (list 11.9895 101.932) 
                         "c"
         )
        (command "pline" (list 12.7237 102.117) "w" 0 0 
                         (list 12.707 102.126) 
                         (list 12.6969 102.123) 
                         (list 12.6401 102.152) 
                         (list 12.6452 102.162) 
                         (list 12.625 102.155) 
                         (list 12.6316 102.135) 
                         (list 12.6367 102.145) 
                         (list 12.6935 102.116) 
                         (list 12.6967 102.106) 
                         (list 12.7134 102.097) 
                         "c"
         )
        (command "pline" (list 12.5921 102.12) "w" 0 0 
                         (list 12.5765 102.128) 
                         (list 12.5671 102.125) 
                         (list 12.5141 102.152) 
                         (list 12.5188 102.161) 
                         (list 12.5 102.155) 
                         (list 12.5061 102.136) 
                         (list 12.5109 102.146) 
                         (list 12.5639 102.119) 
                         (list 12.567 102.109) 
                         (list 12.5826 102.101) 
                         "c"
         )
        (command "pline" (list 12.4462 102.098) "w" 0 0 
                         (list 12.4348 102.109) 
                         (list 12.4256 102.109) 
                         (list 12.3865 102.148) 
                         (list 12.3934 102.155) 
                         (list 12.375 102.155) 
                         (list 12.375 102.137) 
                         (list 12.3819 102.144) 
                         (list 12.421 102.104) 
                         (list 12.421 102.095) 
                         (list 12.4325 102.084) 
                         "c"
         )
        (command "pline" (list 12.3114 102.087) "w" 0 0 
                         (list 12.3018 102.1) 
                         (list 12.2927 102.102) 
                         (list 12.2603 102.146) 
                         (list 12.2682 102.152) 
                         (list 12.25 102.155) 
                         (list 12.2471 102.137) 
                         (list 12.255 102.143) 
                         (list 12.2875 102.098) 
                         (list 12.286 102.089) 
                         (list 12.2956 102.076) 
                         "c"
         )
        (command "pline" (list 12.1624 102.071) "w" 0 0 
                         (list 12.1574 102.087) 
                         (list 12.1492 102.091) 
                         (list 12.1321 102.144) 
                         (list 12.1414 102.147) 
                         (list 12.125 102.155) 
                         (list 12.1167 102.139) 
                         (list 12.1259 102.142) 
                         (list 12.143 102.089) 
                         (list 12.1388 102.081) 
                         (list 12.1438 102.065) 
                         "c"
         )
        (command "pline" (list 12.0098 102.064) "w" 0 0 
                         (list 12.0098 102.08) 
                         (list 12.0033 102.087) 
                         (list 12.0033 102.142) 
                         (list 12.013 102.142) 
                         (list 12.0 102.155) 
                         (list 11.987 102.142) 
                         (list 11.9968 102.142) 
                         (list 11.9968 102.087) 
                         (list 11.9903 102.08) 
                         (list 11.9903 102.064) 
                         "c"
         )
        (command "pline" (list 12.7283 102.258) "w" 0 0 
                         (list 12.7105 102.264) 
                         (list 12.7011 102.259) 
                         (list 12.6404 102.279) 
                         (list 12.6439 102.29) 
                         (list 12.625 102.28) 
                         (list 12.6346 102.261) 
                         (list 12.6381 102.272) 
                         (list 12.6987 102.252) 
                         (list 12.7036 102.243) 
                         (list 12.7214 102.237) 
                         "c"
         )
        (command "pline" (list 12.5964 102.26) "w" 0 0 
                         (list 12.5798 102.265) 
                         (list 12.571 102.261) 
                         (list 12.5144 102.279) 
                         (list 12.5176 102.289) 
                         (list 12.5 102.28) 
                         (list 12.509 102.262) 
                         (list 12.5122 102.272) 
                         (list 12.5688 102.254) 
                         (list 12.5733 102.245) 
                         (list 12.59 102.24) 
                         "c"
         )
        (command "pline" (list 12.4544 102.234) "w" 0 0 
                         (list 12.4412 102.244) 
                         (list 12.4321 102.243) 
                         (list 12.3874 102.275) 
                         (list 12.3932 102.283) 
                         (list 12.375 102.28) 
                         (list 12.3779 102.262) 
                         (list 12.3836 102.27) 
                         (list 12.4283 102.237) 
                         (list 12.4297 102.228) 
                         (list 12.4429 102.219) 
                         "c"
         )
        (command "pline" (list 12.3158 102.227) "w" 0 0 
                         (list 12.3052 102.238) 
                         (list 12.2967 102.238) 
                         (list 12.2606 102.274) 
                         (list 12.267 102.28) 
                         (list 12.25 102.28) 
                         (list 12.25 102.263) 
                         (list 12.2564 102.269) 
                         (list 12.2924 102.233) 
                         (list 12.2924 102.225) 
                         (list 12.303 102.214) 
                         "c"
         )
        (command "pline" (list 12.1712 102.209) "w" 0 0 
                         (list 12.1643 102.223) 
                         (list 12.1563 102.225) 
                         (list 12.1331 102.271) 
                         (list 12.1411 102.275) 
                         (list 12.125 102.28) 
                         (list 12.1198 102.264) 
                         (list 12.1278 102.268) 
                         (list 12.1509 102.223) 
                         (list 12.1483 102.214) 
                         (list 12.1551 102.201) 
                         "c"
         )
        (command "pline" (list 12.009 102.196) "w" 0 0 
                         (list 12.009 102.211) 
                         (list 12.003 102.217) 
                         (list 12.003 102.268) 
                         (list 12.012 102.268) 
                         (list 12.0 102.28) 
                         (list 11.988 102.268) 
                         (list 11.997 102.268) 
                         (list 11.997 102.217) 
                         (list 11.991 102.211) 
                         (list 11.991 102.196) 
                         "c"
         )
        (command "pline" (list 12.7305 102.4) "w" 0 0 
                         (list 12.7119 102.403) 
                         (list 12.7034 102.396) 
                         (list 12.6404 102.406) 
                         (list 12.6422 102.417) 
                         (list 12.625 102.405) 
                         (list 12.6375 102.388) 
                         (list 12.6392 102.399) 
                         (list 12.7022 102.389) 
                         (list 12.7084 102.38) 
                         (list 12.7269 102.377) 
                         "c"
         )
        (command "pline" (list 12.5984 102.4) "w" 0 0 
                         (list 12.5812 102.403) 
                         (list 12.5731 102.397) 
                         (list 12.5144 102.406) 
                         (list 12.516 102.417) 
                         (list 12.5 102.405) 
                         (list 12.5116 102.389) 
                         (list 12.5133 102.399) 
                         (list 12.572 102.39) 
                         (list 12.5779 102.382) 
                         (list 12.5952 102.379) 
                         "c"
         )
        (command "pline" (list 12.4646 102.386) "w" 0 0 
                         (list 12.4491 102.391) 
                         (list 12.4409 102.387) 
                         (list 12.3884 102.404) 
                         (list 12.3914 102.413) 
                         (list 12.375 102.405) 
                         (list 12.3833 102.389) 
                         (list 12.3864 102.398) 
                         (list 12.4389 102.381) 
                         (list 12.4431 102.373) 
                         (list 12.4585 102.368) 
                         "c"
         )
        (command "pline" (list 12.3289 102.375) "w" 0 0 
                         (list 12.3156 102.382) 
                         (list 12.3075 102.379) 
                         (list 12.2621 102.402) 
                         (list 12.2661 102.41) 
                         (list 12.25 102.405) 
                         (list 12.2552 102.389) 
                         (list 12.2593 102.397) 
                         (list 12.3048 102.374) 
                         (list 12.3074 102.366) 
                         (list 12.3208 102.359) 
                         "c"
         )
        (command "pline" (list 12.1853 102.356) "w" 0 0 
                         (list 12.1756 102.366) 
                         (list 12.1678 102.366) 
                         (list 12.1347 102.399) 
                         (list 12.1406 102.405) 
                         (list 12.125 102.405) 
                         (list 12.125 102.389) 
                         (list 12.1308 102.395) 
                         (list 12.1639 102.362) 
                         (list 12.1639 102.354) 
                         (list 12.1736 102.345) 
                         "c"
         )
        (command "pline" (list 12.0083 102.328) "w" 0 0 
                         (list 12.0083 102.342) 
                         (list 12.0028 102.347) 
                         (list 12.0028 102.394) 
                         (list 12.011 102.394) 
                         (list 12.0 102.405) 
                         (list 11.989 102.394) 
                         (list 11.9972 102.394) 
                         (list 11.9972 102.347) 
                         (list 11.9918 102.342) 
                         (list 11.9918 102.328) 
                         "c"
         )
        (command "pline" (list 12.598 102.54) "w" 0 0 
                         (list 12.5805 102.54) 
                         (list 12.5735 102.534) 
                         (list 12.514 102.534) 
                         (list 12.514 102.544) 
                         (list 12.5 102.53) 
                         (list 12.514 102.516) 
                         (list 12.514 102.527) 
                         (list 12.5735 102.527) 
                         (list 12.5805 102.52) 
                         (list 12.598 102.52) 
                         "c"
         )
        (command "pline" (list 12.5952 102.681) "w" 0 0 
                         (list 12.5779 102.678) 
                         (list 12.572 102.67) 
                         (list 12.5133 102.661) 
                         (list 12.5116 102.671) 
                         (list 12.5 102.655) 
                         (list 12.516 102.643) 
                         (list 12.5144 102.654) 
                         (list 12.5731 102.663) 
                         (list 12.5812 102.657) 
                         (list 12.5984 102.66) 
                         "c"
         )
        (command "pline" (list 12.59 102.82) "w" 0 0 
                         (list 12.5733 102.815) 
                         (list 12.5688 102.806) 
                         (list 12.5122 102.788) 
                         (list 12.509 102.798) 
                         (list 12.5 102.78) 
                         (list 12.5176 102.771) 
                         (list 12.5144 102.781) 
                         (list 12.571 102.799) 
                         (list 12.5798 102.795) 
                         (list 12.5964 102.8) 
                         "c"
         )
        (command "pline" (list 12.5826 102.959) "w" 0 0 
                         (list 12.567 102.951) 
                         (list 12.5639 102.941) 
                         (list 12.5109 102.914) 
                         (list 12.5061 102.924) 
                         (list 12.5 102.905) 
                         (list 12.5188 102.899) 
                         (list 12.5141 102.908) 
                         (list 12.5671 102.935) 
                         (list 12.5765 102.932) 
                         (list 12.5921 102.94) 
                         "c"
         )
        (command "pline" (list 12.5619 103.107) "w" 0 0 
                         (list 12.5495 103.094) 
                         (list 12.5495 103.084) 
                         (list 12.5074 103.042) 
                         (list 12.5 103.05) 
                         (list 12.5 103.03) 
                         (list 12.5198 103.03) 
                         (list 12.5124 103.037) 
                         (list 12.5544 103.079) 
                         (list 12.5643 103.079) 
                         (list 12.5767 103.092) 
                         "c"
         )
        (command "pline" (list 12.4101 103.122) "w" 0 0 
                         (list 12.4022 103.106) 
                         (list 12.4053 103.097) 
                         (list 12.3782 103.044) 
                         (list 12.3689 103.049) 
                         (list 12.375 103.03) 
                         (list 12.3938 103.036) 
                         (list 12.3845 103.041) 
                         (list 12.4115 103.094) 
                         (list 12.4209 103.097) 
                         (list 12.4288 103.113) 
                         "c"
         )
        (command "pline" (list 12.2703 103.126) "w" 0 0 
                         (list 12.2649 103.11) 
                         (list 12.2694 103.101) 
                         (list 12.251 103.044) 
                         (list 12.241 103.048) 
                         (list 12.25 103.03) 
                         (list 12.2676 103.039) 
                         (list 12.2577 103.042) 
                         (list 12.276 103.099) 
                         (list 12.2849 103.103) 
                         (list 12.2903 103.12) 
                         "c"
         )
        (command "pline" (list 12.1736 102.715) "w" 0 0 
                         (list 12.1639 102.706) 
                         (list 12.1639 102.698) 
                         (list 12.1308 102.665) 
                         (list 12.125 102.671) 
                         (list 12.125 102.655) 
                         (list 12.1406 102.655) 
                         (list 12.1347 102.661) 
                         (list 12.1678 102.694) 
                         (list 12.1756 102.694) 
                         (list 12.1853 102.704) 
                         "c"
         )
        (command "pline" (list 12.334 102.539) "w" 0 0 
                         (list 12.319 102.539) 
                         (list 12.313 102.533) 
                         (list 12.262 102.533) 
                         (list 12.262 102.542) 
                         (list 12.25 102.53) 
                         (list 12.262 102.518) 
                         (list 12.262 102.527) 
                         (list 12.313 102.527) 
                         (list 12.319 102.521) 
                         (list 12.334 102.521) 
                         "c"
         )
        (command "pline" (list 12.3208 102.701) "w" 0 0 
                         (list 12.3074 102.694) 
                         (list 12.3048 102.686) 
                         (list 12.2593 102.663) 
                         (list 12.2552 102.671) 
                         (list 12.25 102.655) 
                         (list 12.2661 102.65) 
                         (list 12.2621 102.658) 
                         (list 12.3075 102.681) 
                         (list 12.3156 102.678) 
                         (list 12.3289 102.685) 
                         "c"
         )
        (command "pline" (list 12.303 102.846) "w" 0 0 
                         (list 12.2924 102.835) 
                         (list 12.2924 102.827) 
                         (list 12.2564 102.791) 
                         (list 12.25 102.797) 
                         (list 12.25 102.78) 
                         (list 12.267 102.78) 
                         (list 12.2606 102.786) 
                         (list 12.2967 102.822) 
                         (list 12.3052 102.822) 
                         (list 12.3158 102.833) 
                         "c"
         )
        (command "pline" (list 12.1551 102.859) "w" 0 0 
                         (list 12.1483 102.846) 
                         (list 12.1509 102.837) 
                         (list 12.1278 102.792) 
                         (list 12.1198 102.796) 
                         (list 12.125 102.78) 
                         (list 12.1411 102.785) 
                         (list 12.1331 102.789) 
                         (list 12.1563 102.835) 
                         (list 12.1643 102.837) 
                         (list 12.1712 102.851) 
                         "c"
         )
        (command "pline" (list 12.466 102.54) "w" 0 0 
                         (list 12.4498 102.54) 
                         (list 12.4433 102.533) 
                         (list 12.388 102.533) 
                         (list 12.388 102.543) 
                         (list 12.375 102.53) 
                         (list 12.388 102.517) 
                         (list 12.388 102.527) 
                         (list 12.4433 102.527) 
                         (list 12.4498 102.52) 
                         (list 12.466 102.52) 
                         "c"
         )
        (command "pline" (list 12.4585 102.692) "w" 0 0 
                         (list 12.4431 102.687) 
                         (list 12.4389 102.679) 
                         (list 12.3864 102.662) 
                         (list 12.3833 102.671) 
                         (list 12.375 102.655) 
                         (list 12.3914 102.647) 
                         (list 12.3884 102.656) 
                         (list 12.4409 102.673) 
                         (list 12.4491 102.669) 
                         (list 12.4646 102.674) 
                         "c"
         )
        (command "pline" (list 12.4429 102.841) "w" 0 0 
                         (list 12.4297 102.832) 
                         (list 12.4283 102.823) 
                         (list 12.3836 102.79) 
                         (list 12.3779 102.798) 
                         (list 12.375 102.78) 
                         (list 12.3932 102.777) 
                         (list 12.3874 102.785) 
                         (list 12.4321 102.817) 
                         (list 12.4412 102.816) 
                         (list 12.4544 102.826) 
                         "c"
         )
        (command "pline" (list 12.4325 102.976) "w" 0 0 
                         (list 12.421 102.965) 
                         (list 12.421 102.956) 
                         (list 12.3819 102.916) 
                         (list 12.375 102.923) 
                         (list 12.375 102.905) 
                         (list 12.3934 102.905) 
                         (list 12.3865 102.912) 
                         (list 12.4256 102.951) 
                         (list 12.4348 102.951) 
                         (list 12.4462 102.962) 
                         "c"
         )
        (command "pline" (list 12.2956 102.984) "w" 0 0 
                         (list 12.286 102.971) 
                         (list 12.2875 102.962) 
                         (list 12.255 102.917) 
                         (list 12.2471 102.923) 
                         (list 12.25 102.905) 
                         (list 12.2682 102.908) 
                         (list 12.2603 102.914) 
                         (list 12.2927 102.958) 
                         (list 12.3018 102.96) 
                         (list 12.3114 102.973) 
                         "c"
         )
        (command "pline" (list 12.1438 102.995) "w" 0 0 
                         (list 12.1388 102.979) 
                         (list 12.143 102.971) 
                         (list 12.1259 102.918) 
                         (list 12.1167 102.921) 
                         (list 12.125 102.905) 
                         (list 12.1414 102.913) 
                         (list 12.1321 102.916) 
                         (list 12.1492 102.969) 
                         (list 12.1574 102.973) 
                         (list 12.1624 102.989) 
                         "c"
         )
        (command "pline" (list 12.202 102.538) "w" 0 0 
                         (list 12.1883 102.538) 
                         (list 12.1828 102.533) 
                         (list 12.136 102.533) 
                         (list 12.136 102.541) 
                         (list 12.125 102.53) 
                         (list 12.136 102.519) 
                         (list 12.136 102.527) 
                         (list 12.1828 102.527) 
                         (list 12.1883 102.522) 
                         (list 12.202 102.522) 
                         "c"
         )
        (command "pline" (list 12.08 102.537) "w" 0 0 
                         (list 12.0675 102.537) 
                         (list 12.0625 102.533) 
                         (list 12.02 102.533) 
                         (list 12.02 102.54) 
                         (list 12.01 102.53) 
                         (list 12.02 102.52) 
                         (list 12.02 102.528) 
                         (list 12.0625 102.528) 
                         (list 12.0675 102.523) 
                         (list 12.08 102.523) 
                         "c"
         )
        (command "pline" (list 12.0075 102.45) "w" 0 0 
                         (list 12.0075 102.463) 
                         (list 12.0025 102.468) 
                         (list 12.0025 102.51) 
                         (list 12.01 102.51) 
                         (list 12.0 102.52) 
                         (list 11.99 102.51) 
                         (list 11.9975 102.51) 
                         (list 11.9975 102.468) 
                         (list 11.9925 102.463) 
                         (list 11.9925 102.45) 
                         "c"
         )
        (command "pline" (list 11.92 102.523) "w" 0 0 
                         (list 11.9325 102.523) 
                         (list 11.9375 102.528) 
                         (list 11.98 102.528) 
                         (list 11.98 102.52) 
                         (list 11.99 102.53) 
                         (list 11.98 102.54) 
                         (list 11.98 102.533) 
                         (list 11.9375 102.533) 
                         (list 11.9325 102.537) 
                         (list 11.92 102.537) 
                         "c"
         )
        (command "pline" (list 11.9925 102.61) "w" 0 0 
                         (list 11.9925 102.598) 
                         (list 11.9975 102.593) 
                         (list 11.9975 102.55) 
                         (list 11.99 102.55) 
                         (list 12.0 102.54) 
                         (list 12.01 102.55) 
                         (list 12.0025 102.55) 
                         (list 12.0025 102.593) 
                         (list 12.0075 102.598) 
                         (list 12.0075 102.61) 
                         "c"
         )
  
  );画6寸的reticle\pellicle\MVS图形


(defun ins_1(basepoint / ent ss)
        (setq ss (ssadd))
        (command "pline" (list 2.55 0.0) "w" 0 0
                         (list 2.1 0.0)
                         (list 2.1 5.0) 
                         (list 2.55 5.0) 
                         "c"
        )
  	(setq ent (entlast))
  	(ssadd ent ss)
        (command "pline" (list 1.7 0.0) "w" 0 0 
                         (list 1.9 0.0) 
                         (list 1.9 5.0) 
                         (list 1.7 5.0) 
                         "c"
        )
  	(setq ent (entlast))
  	(ssadd ent ss)
        (command "pline" (list 1.3 0.0) "w" 0 0 
                         (list 1.5 0.0) 
                         (list 1.5 5.0) 
                         (list 1.3 5.0) 
                         "c"
        )
  	(setq ent (entlast))
  	(ssadd ent ss)
        (command "pline" (list 0.45 0.0) "w" 0 0 
                         (list 0.0 0.0) 
                         (list 0.0 5.0) 
                         (list 0.45 5.0) 
                         "c"
        )
  	(setq ent (entlast))
  	(ssadd ent ss)
        (command "pline" (list 0.65 0.0) "w" 0 0 
                         (list 0.85 0.0) 
                         (list 0.85 5.0)
                         (list 0.65 5.0) 
                         "c"
        )
  	(setq ent (entlast))
  	(ssadd ent ss)
  	(command "move" ss "" "0,0" basepoint)
  )
(defun ins_2(basepoint / ent ss)
  	  (setq ss (ssadd))
  	  (command "pline" (list 0.0 0.0) "w" 0 0 
                         (list 0.2 0.0) 
                         (list 0.2 5.0) 
                         (list 0.0 5.0) 
                         "c"
         )
  	(setq ent (entlast))
  	(ssadd ent ss)
        (command "pline" (list 0.85 0.0) "w" 0 0 
                         (list 0.4 0.0) 
                         (list 0.4 5.0) 
                         (list 0.85 5.0) 
                         "c"
         )
   	(setq ent (entlast))
  	(ssadd ent ss)
        (command "pline" (list 1.3 0.0) "w" 0 0 
                         (list 1.5 0.0) 
                         (list 1.5 5.0) 
                         (list 1.3 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "move" ss "" "0,0" basepoint)
  )
(defun ins_3(basepoint / ent ss)
  	 (setq ss (ssadd))
  	 (command "pline" (list 1.1 0.0) "w" 0 0 
                         (list 0.65 0.0) 
                         (list 0.65 5.0) 
                         (list 1.1 5.0) 
                         "c"
         )
  	(setq ent (entlast))
  	(ssadd ent ss)
        (command "pline" (list 1.95 0.0) "w" 0 0 
                         (list 2.15 0.0) 
                         (list 2.15 5.0) 
                         (list 1.95 5.0) 
                         "c"
         )
  	(setq ent (entlast))
  	(ssadd ent ss)
        (command "pline" (list 1.55 0.0) "w" 0 0 
                         (list 1.75 0.0) 
                         (list 1.75 5.0) 
                         (list 1.55 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
  	(command "move" ss "" "0,0" basepoint)
  )

(defun ins_4(basepoint / ent ss)
  	 (setq ss (ssadd))
  	 (command "pline" (list 1.7 0.0) "w" 0 0 
                         (list 1.9 0.0) 
                         (list 1.9 5.0) 
                         (list 1.7 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 0.4 0.0) "w" 0 0 
                         (list 0.6 0.0) 
                         (list 0.6 5.0) 
                         (list 0.4 5.0) 
                         "c"
         )
    	(setq ent (entlast))
  	(ssadd ent ss)
        (command "pline" (list 1.5 0.0) "w" 0 0 
                         (list 1.05 0.0) 
                         (list 1.05 5.0) 
                         (list 1.5 5.0) 
                         "c"
         )
    	(setq ent (entlast))
  	(ssadd ent ss)
  	(command "move" ss "" "0,0" basepoint)
  )

(defun ins_5(basepoint / ent ss)
  	(setq ss (ssadd))
  	(command "pline" (list 0.45 0.0) "w" 0 0 
                         (list 0.0 0.0) 
                         (list 0.0 5.0) 
                         (list 0.45 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
        (command "pline" (list 1.75 0.0) "w" 0 0 
                         (list 1.3 0.0) 
                         (list 1.3 5.0) 
                         (list 1.75 5.0) 
                         "c"
         )
  	(setq ent (entlast))
  	(ssadd ent ss)
        (command "pline" (list 1.95 0.0) "w" 0 0 
                         (list 2.15 0.0) 
                         (list 2.15 5.0) 
                         (list 1.95 5.0) 
                         "c"
         )
  	(setq ent (entlast))
  	(ssadd ent ss)
  	(command "move" ss "" "0,0" basepoint)  	
  )

(defun ins_6(basepoint / ent ss)
  	(setq ss (ssadd))
  	(command "pline" (list 1.95 0.0) "w" 0 0 
                         (list 2.15 0.0) 
                         (list 2.15 5.0) 
                         (list 1.95 5.0) 
                         "c"
         )
  	(setq ent (entlast))
  	(ssadd ent ss)
        (command "pline" (list 1.75 0.0) "w" 0 0 
                         (list 1.3 0.0) 
                         (list 1.3 5.0) 
                         (list 1.75 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.85 0.0) "w" 0 0 
                         (list 0.4 0.0) 
                         (list 0.4 5.0) 
                         (list 0.85 5.0) 
                         "c"
         )
  	(setq ent (entlast))
  	(ssadd ent ss)
  	(command "move" ss "" "0,0" basepoint)
  )
(defun ins_7(basepoint / ent ss)
  	(setq ss (ssadd))
  	(command "pline" (list 0.4 0.0) "w" 0 0 
                         (list 0.6 0.0) 
                         (list 0.6 5.0) 
                         (list 0.4 5.0) 
                         "c"
         )
  	(setq ent (entlast))
  	(ssadd ent ss)
                (command "pline" (list 2.55 0.0) "w" 0 0 
                         (list 2.1 0.0) 
                         (list 2.1 5.0) 
                         (list 2.55 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
                (command "pline" (list 1.9 0.0) "w" 0 0 
                         (list 1.45 0.0) 
                         (list 1.45 5.0) 
                         (list 1.9 5.0) 
                         "c"
         )
  	(setq ent (entlast))
  	(ssadd ent ss)
  	(command "move" ss "" "0,0" basepoint)
  )

(defun ins_8(basepoint / ent ss)
  	(setq ss (ssadd))
  	(command "pline" (list 1.3 0.0) "w" 0 0 
                         (list 1.5 0.0) 
                         (list 1.5 5.0) 
                         (list 1.3 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
  	(command "move" ss "" "0,0" basepoint)
  )

(defun ins_9(basepoint / ent ss)
  	(setq ss (ssadd))
  	(command "pline" (list 0.85 0.0) "w" 0 0 
                         (list 0.4 0.0) 
                         (list 0.4 5.0) 
                         (list 0.85 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
         (command "pline" (list 0.0 0.0) "w" 0 0 
                         (list 0.2 0.0) 
                         (list 0.2 5.0) 
                         (list 0.0 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 1.3 0.0) "w" 0 0 
                         (list 1.5 0.0) 
                         (list 1.5 5.0) 
                         (list 1.3 5.0) 
                         "c"
         )
  	(setq ent (entlast))
  	(ssadd ent ss)
  	(command "move" ss "" "0,0" basepoint)
  )(defun ins_0(basepoint / ent ss)
  	(setq ss (ssadd))
  	(command "pline" (list 1.5 0.0) "w" 0 0 
                         (list 1.05 0.0) 
                         (list 1.05 5.0) 
                         (list 1.5 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 0.4 0.0) "w" 0 0 
                         (list 0.6 0.0) 
                         (list 0.6 5.0) 
                         (list 0.4 5.0) 
                         "c"
         )
  	(setq ent (entlast))
  	(ssadd ent ss)
  	(command "move" ss "" "0,0" basepoint)
  )

(defun ins_a(basepoint / ent ss)
  	(setq ss (ssadd))
  	(command "pline" (list 0.65 0.0) "w" 0 0 
                         (list 0.85 0.0) 
                         (list 0.85 5.0) 
                         (list 0.65 5.0) 
                         "c"
         )
  	(setq ent (entlast))
  	(ssadd ent ss)
         (command "pline" (list 0.45 0.0) "w" 0 0 
                         (list 0.0 0.0) 
                         (list 0.0 5.0) 
                         (list 0.45 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
  	(command "move" ss "" "0,0" basepoint)
  )

(defun ins_b(basepoint / ent ss)
  	(setq ss (ssadd))
  	(command "pline" (list 2.55 0.0) "w" 0 0 
                         (list 2.1 0.0) 
                         (list 2.1 5.0) 
                         (list 2.55 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
         (command "pline" (list 0.85 0.0) "w" 0 0 
                         (list 0.4 0.0) 
                         (list 0.4 5.0) 
                         (list 0.85 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
  	(command "move" ss "" "0,0" basepoint)
  )

(defun ins_c(basepoint / ent ss)
  	(setq ss (ssadd))
  	(command "pline" (list 2.35 0.0) "w" 0 0 
                         (list 2.55 0.0) 
                         (list 2.55 5.0) 
                         (list 2.35 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
        (command "pline" (list 1.3 0.0) "w" 0 0 
                         (list 1.5 0.0) 
                         (list 1.5 5.0) 
                         (list 1.3 5.0) 
                         "c"
         )
  	(setq ent (entlast))
  	(ssadd ent ss)
        (command "pline" (list 1.95 0.0) "w" 0 0 
                         (list 2.15 0.0) 
                         (list 2.15 5.0) 
                         (list 1.95 5.0) 
                         "c"
         )
  	(setq ent (entlast))
  	(ssadd ent ss)
        (command "pline" (list 1.1 0.0) "w" 0 0 
                         (list 0.65 0.0) 
                         (list 0.65 5.0) 
                         (list 1.1 5.0) 
                         "c"
         )
  	(setq ent (entlast))
  	(ssadd ent ss)
  	(command "move" ss "" "0,0" basepoint)
  )

(defun ins_d(basepoint / ent ss)
  	(setq ss (ssadd))
  	(command "pline" (list 1.25 0.0) "w" 0 0 
                         (list 0.8 0.0) 
                         (list 0.8 5.0) 
                         (list 1.25 5.0) 
                         "c"
         )
  	(setq ent (entlast))
  	(ssadd ent ss)
         (command "pline" (list 0.4 0.0) "w" 0 0 
                         (list 0.6 0.0) 
                         (list 0.6 5.0) 
                         (list 0.4 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
  	(command "move" ss "" "0,0" basepoint)
  )

(defun ins_e(basepoint / ent ss)
  	(setq ss (ssadd))
  	(command "pline" (list 1.95 0.0) "w" 0 0 
                         (list 2.15 0.0) 
                         (list 2.15 5.0) 
                         (list 1.95 5.0) 
                         "c"
         )
  	(setq ent (entlast))
  	(ssadd ent ss)
          (command "pline" (list 1.5 0.0) "w" 0 0 
                         (list 1.05 0.0) 
                         (list 1.05 5.0) 
                         (list 1.5 5.0) 
                         "c"
         )
  	(setq ent (entlast))
  	(ssadd ent ss)
         (command "pline" (list 0.65 0.0) "w" 0 0 
                         (list 0.85 0.0) 
                         (list 0.85 5.0) 
                         (list 0.65 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
  	(command "move" ss "" "0,0" basepoint)
  )

(defun ins_f(basepoint / ent ss)
  	(setq ss (ssadd))
  	(command "pline" (list 0.85 0.0) "w" 0 0 
                         (list 0.4 0.0) 
                         (list 0.4 5.0) 
                         (list 0.85 5.0) 
                         "c"
         )
  	(setq ent (entlast))
  	(ssadd ent ss)
          (command "pline" (list 2.35 0.0) "w" 0 0 
                         (list 2.55 0.0) 
                         (list 2.55 5.0) 
                         (list 2.35 5.0) 
                         "c"
         )
  	(setq ent (entlast))
  	(ssadd ent ss)
         (command "pline" (list 0.0 0.0) "w" 0 0 
                         (list 0.2 0.0) 
                         (list 0.2 5.0) 
                         (list 0.0 5.0) 
                         "c"
         )
  	(setq ent (entlast))
  	(ssadd ent ss)
          (command "pline" (list 1.5 0.0) "w" 0 0 
                         (list 1.05 0.0) 
                         (list 1.05 5.0) 
                         (list 1.5 5.0) 
                         "c"
         )
  	(setq ent (entlast))
  	(ssadd ent ss)
        (command "pline" (list 1.95 0.0) "w" 0 0 
                         (list 2.15 0.0) 
                         (list 2.15 5.0) 
                         (list 1.95 5.0) 
                         "c"
         )
  	(setq ent (entlast))
  	(ssadd ent ss)
  	(command "move" ss "" "0,0" basepoint)
  )

(defun ins_g(basepoint / ent ss)
  	(setq ss (ssadd))
  	(command "pline" (list 1.9 0.0) "w" 0 0 
                         (list 1.45 0.0) 
                         (list 1.45 5.0) 
                         (list 1.9 5.0) 
                         "c"
         )
  	(setq ent (entlast))
  	(ssadd ent ss)
        (command "pline" (list 0.8 0.0) "w" 0 0 
                         (list 1.0 0.0) 
                         (list 1.0 5.0) 
                         (list 0.8 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 0.4 0.0) "w" 0 0 
                         (list 0.6 0.0) 
                         (list 0.6 5.0) 
                         (list 0.4 5.0) 
                         "c"
         )
  	(setq ent (entlast))
  	(ssadd ent ss)
  	(command "move" ss "" "0,0" basepoint)
  )

(defun ins_h(basepoint / ent ss)
  	(setq ss (ssadd))
  	 (command "pline" (list 0.45 0.0) "w" 0 0 
                         (list 0.0 0.0) 
                         (list 0.0 5.0) 
                         (list 0.45 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
  	(command "move" ss "" "0,0" basepoint)
  )

(defun ins_i(basepoint / ent ss)
  	(setq ss (ssadd))
  	 (command "pline" (list 1.05 0.0) "w" 0 0 
                         (list 1.25 0.0) 
                         (list 1.25 5.0) 
                         (list 1.05 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.85 0.0) "w" 0 0 
                         (list 0.4 0.0) 
                         (list 0.4 5.0) 
                         (list 0.85 5.0) 
                         "c"
        )
  	(setq ent (entlast))
  	(ssadd ent ss)
  	(command "move" ss "" "0,0" basepoint)
  )


(defun ins_j(basepoint / ent ss)
  	(setq ss (ssadd))
  	 (command "pline" (list 0.4 0.0) "w" 0 0 
                         (list 0.6 0.0) 
                         (list 0.6 5.0) 
                         (list 0.4 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 1.25 0.0) "w" 0 0 
                         (list 0.8 0.0) 
                         (list 0.8 5.0) 
                         (list 1.25 5.0) 
                         "c"
         )
  	(setq ent (entlast))
  	(ssadd ent ss)
  	(command "move" ss "" "0,0" basepoint)
  )


(defun ins_k(basepoint / ent ss)
  	(setq ss (ssadd))
  	  (command "pline" (list 2.55 0.0) "w" 0 0 
                         (list 2.1 0.0) 
                         (list 2.1 5.0) 
                         (list 2.55 5.0) 
                         "c"
         )
  	(setq ent (entlast))
  	(ssadd ent ss)
        (command "pline" (list 1.45 0.0) "w" 0 0 
                         (list 1.65 0.0) 
                         (list 1.65 5.0) 
                         (list 1.45 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
  	(command "move" ss "" "0,0" basepoint)
  )

(defun ins_l(basepoint / ent ss)
  	(setq ss (ssadd))
  	  (command "pline" (list 0.0 0.0) "w" 0 0 
                         (list 0.2 0.0) 
                         (list 0.2 5.0) 
                         (list 0.0 5.0) 
                         "c"
         )
  	(setq ent (entlast))
  	(ssadd ent ss)
        (command "pline" (list 0.85 0.0) "w" 0 0 
                         (list 0.4 0.0) 
                         (list 0.4 5.0) 
                         (list 0.85 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
         (command "pline" (list 1.45 0.0) "w" 0 0 
                         (list 1.65 0.0) 
                         (list 1.65 5.0) 
                         (list 1.45 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
  	(command "move" ss "" "0,0" basepoint)
  )


(defun ins_m(basepoint / ent ss)
  	(setq ss (ssadd))
  	  (command "pline" (list 1.1 0.0) "w" 0 0 
                         (list 0.65 0.0) 
                         (list 0.65 5.0) 
                         (list 1.1 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
        (command "pline" (list 1.3 0.0) "w" 0 0 
                         (list 1.5 0.0) 
                         (list 1.5 5.0) 
                         (list 1.3 5.0) 
                         "c"
         )
  	(setq ent (entlast))
  	(ssadd ent ss)
         (command "pline" (list 0.45 0.0) "w" 0 0 
                         (list 0.0 0.0) 
                         (list 0.0 5.0) 
                         (list 0.45 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
  	(command "move" ss "" "0,0" basepoint)
  )

(defun ins_n(basepoint / ent ss)
  	(setq ss (ssadd))
  	  (command "pline" (list 1.45 0.0) "w" 0 0 
                         (list 1.65 0.0) 
                         (list 1.65 5.0) 
                         (list 1.45 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
         (command "pline" (list 0.4 0.0) "w" 0 0 
                         (list 0.6 0.0) 
                         (list 0.6 5.0) 
                         (list 0.4 5.0) 
                         "c"
         )
  	(setq ent (entlast))
  	(ssadd ent ss)
        (command "pline" (list 1.25 0.0) "w" 0 0 
                         (list 0.8 0.0) 
                         (list 0.8 5.0) 
                         (list 1.25 5.0) 
                         "c"
         )
  	(setq ent (entlast))
  	(ssadd ent ss)
  	(command "move" ss "" "0,0" basepoint)
  )

(defun ins_o(basepoint / ent ss)
  	(setq ss (ssadd))
  	(command "pline" (list 0.45 0.0) "w" 0 0 
                         (list 0.0 0.0) 
                         (list 0.0 5.0) 
                         (list 0.45 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
         (command "pline" (list 1.5 0.0) "w" 0 0 
                         (list 1.05 0.0) 
                         (list 1.05 5.0) 
                         (list 1.5 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
  	(command "move" ss "" "0,0" basepoint)
  )

(defun ins_p(basepoint / ent ss)
  	(setq ss (ssadd))
  	(command "pline" (list 1.7 0.0) "w" 0 0 
                         (list 1.9 0.0)
                         (list 1.9 5.0) 
                         (list 1.7 5.0) 
                         "c"
         )
  	(setq ent (entlast))
  	(ssadd ent ss)
        (command "pline" (list 1.5 0.0) "w" 0 0 
                         (list 1.05 0.0) 
                         (list 1.05 5.0) 
                         (list 1.5 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
         (command "pline" (list 2.35 0.0) "w" 0 0 
                         (list 2.55 0.0) 
                         (list 2.55 5.0) 
                         (list 2.35 5.0) 
                         "c"
         )
  	(setq ent (entlast))
  	(ssadd ent ss)
        (command "pline" (list 0.85 0.0) "w" 0 0 
                         (list 0.4 0.0) 
                         (list 0.4 5.0) 
                         (list 0.85 5.0) 
                         "c"
         )
  	(setq ent (entlast))
  	(ssadd ent ss)
  	(command "move" ss "" "0,0" basepoint)
  )


(defun ins_q(basepoint / ent ss)
  	(setq ss (ssadd))
  	(command "pline" (list 0.4 0.0) "w" 0 0 
                         (list 0.6 0.0) 
                         (list 0.6 5.0) 
                         (list 0.4 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
         (command "pline" (list 0.8 0.0) "w" 0 0 
                         (list 1.0 0.0) 
                         (list 1.0 5.0) 
                         (list 0.8 5.0) 
                         "c"
         )
  	(setq ent (entlast))
  	(ssadd ent ss)
        (command "pline" (list 1.65 0.0) "w" 0 0 
                         (list 1.2 0.0) 
                         (list 1.2 5.0) 
                         (list 1.65 5.0) 
                         "c"
         )
  	(setq ent (entlast))
  	(ssadd ent ss)
  	(command "move" ss "" "0,0" basepoint)
  )


(defun ins_r(basepoint / ent ss)
  	(setq ss (ssadd))
  	(command "pline" (list 1.05 0.0) "w" 0 0 
                         (list 1.25 0.0) 
                         (list 1.25 5.0) 
                         (list 1.05 5.0) 
                         "c"
         )
  	(setq ent (entlast))
  	(ssadd ent ss)
        (command "pline" (list 1.9 0.0) "w" 0 0 
                         (list 1.45 0.0) 
                         (list 1.45 5.0) 
                         (list 1.9 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
         (command "pline" (list 2.35 0.0) "w" 0 0 
                         (list 2.55 0.0) 
                         (list 2.55 5.0) 
                         (list 2.35 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
  	(command "move" ss "" "0,0" basepoint)
  )


(defun ins_s(basepoint / ent ss)
  	(setq ss (ssadd))
  	(command "pline" (list 0.85 0.0) "w" 0 0 
                         (list 0.4 0.0) 
                         (list 0.4 5.0) 
                         (list 0.85 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
         (command "pline" (list 1.9 0.0) "w" 0 0 
                         (list 1.45 0.0) 
                         (list 1.45 5.0) 
                         (list 1.9 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
  	(command "move" ss "" "0,0" basepoint)
  )


(defun ins_t(basepoint / ent ss)
  	(setq ss (ssadd))
  	(command "pline" (list 1.25 0.0) "w" 0 0 
                         (list 0.8 0.0) 
                         (list 0.8 5.0) 
                         (list 1.25 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
         (command "pline" (list 1.9 0.0) "w" 0 0 
                         (list 1.45 0.0) 
                         (list 1.45 5.0) 
                         (list 1.9 5.0) 
                         "c"
         )
  	(setq ent (entlast))
  	(ssadd ent ss)
        (command "pline" (list 0.4 0.0) "w" 0 0 
                         (list 0.6 0.0) 
                         (list 0.6 5.0) 
                         (list 0.4 5.0) 
                         "c"
         )
  	(setq ent (entlast))
  	(ssadd ent ss)
  	(command "move" ss "" "0,0" basepoint)
  )


(defun ins_u(basepoint / ent ss)
  	(setq ss (ssadd))
  	(command "pline" (list 0.9 0.0) "w" 0 0 
                         (list 1.1 0.0) 
                         (list 1.1 5.0) 
                         (list 0.9 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
        (command "pline" (list 1.3 0.0) "w" 0 0 
                         (list 1.5 0.0) 
                         (list 1.5 5.0) 
                         (list 1.3 5.0) 
                         "c"
         )
  	(setq ent (entlast))
  	(ssadd ent ss)
         (command "pline" (list 1.7 0.0) "w" 0 0 
                         (list 1.9 0.0) 
                         (list 1.9 5.0) 
                         (list 1.7 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
  	(command "move" ss "" "0,0" basepoint)
  )


(defun ins_v(basepoint / ent ss)
  	(setq ss (ssadd))
  	(command "pline" (list 2.55 0.0) "w" 0 0 
                         (list 2.1 0.0) 
                         (list 2.1 5.0) 
                         (list 2.55 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
        (command "pline" (list 1.3 0.0) "w" 0 0 
                         (list 1.5 0.0) 
                         (list 1.5 5.0) 
                         (list 1.3 5.0) 
                         "c"
         )
  	(setq ent (entlast))
  	(ssadd ent ss)
         (command "pline" (list 1.1 0.0) "w" 0 0 
                         (list 0.65 0.0) 
                         (list 0.65 5.0) 
                         (list 1.1 5.0) 
                         "c"
         )
  	(setq ent (entlast))
  	(ssadd ent ss)
         (command "pline" (list 0.0 0.0) "w" 0 0 
                         (list 0.2 0.0) 
                         (list 0.2 5.0) 
                         (list 0.0 5.0) 
                         "c"
         )
  	(setq ent (entlast))
  	(ssadd ent ss)
  	(command "move" ss "" "0,0" basepoint)
  )



(defun ins_w(basepoint / ent ss)
  	(setq ss (ssadd))
  	(command "pline" (list 2.35 0.0) "w" 0 0 
                         (list 2.55 0.0) 
                         (list 2.55 5.0) 
                         (list 2.35 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
        (command "pline" (list 1.55 0.0) "w" 0 0 
                         (list 1.75 0.0) 
                         (list 1.75 5.0) 
                         (list 1.55 5.0) 
                         "c"
         )
  	(setq ent (entlast))
  	(ssadd ent ss)
         (command "pline" (list 1.95 0.0) "w" 0 0 
                         (list 2.15 0.0) 
                         (list 2.15 5.0) 
                         (list 1.95 5.0) 
                         "c"
         )
  	(setq ent (entlast))
  	(ssadd ent ss)
        (command "pline" (list 1.35 0.0) "w" 0 0 
                         (list 0.9 0.0) 
                         (list 0.9 5.0) 
                         (list 1.35 5.0) 
                         "c"
         )
  	(setq ent (entlast))
  	(ssadd ent ss)
  	(command "move" ss "" "0,0" basepoint)
  )



(defun ins_x(basepoint / ent ss)
  	(setq ss (ssadd))
  	(command "pline" (list 1.5 0.0) "w" 0 0 
                         (list 1.05 0.0) 
                         (list 1.05 5.0) 
                         (list 1.5 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 1.7 0.0) "w" 0 0 
                         (list 1.9 0.0) 
                         (list 1.9 5.0) 
                         (list 1.7 5.0) 
                         "c"
         )
  	(setq ent (entlast))
  	(ssadd ent ss)
  	(command "move" ss "" "0,0" basepoint)
  )


(defun ins_y(basepoint / ent ss)
  	(setq ss (ssadd))
  	(command "pline" (list 1.95 0.0) "w" 0 0 
                         (list 2.15 0.0) 
                         (list 2.15 5.0) 
                         (list 1.95 5.0) 
                         "c"
         )
  	(setq ent (entlast))
  	(ssadd ent ss)
        (command "pline" (list 1.75 0.0) "w" 0 0 
                         (list 1.3 0.0) 
                         (list 1.3 5.0) 
                         (list 1.75 5.0) 
                         "c"
         )
  	(setq ent (entlast))
  	(ssadd ent ss)
        (command "pline" (list 0.9 0.0) "w" 0 0 
                         (list 1.1 0.0) 
                         (list 1.1 5.0) 
                         (list 0.9 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.45 0.0) "w" 0 0 
                         (list 0.0 0.0) 
                         (list 0.0 5.0) 
                         (list 0.45 5.0) 
                         "c"
         )
  	(setq ent (entlast))
  	(ssadd ent ss)
  	(command "move" ss "" "0,0" basepoint)
  )


(defun ins_z(basepoint / ent ss)
  	(setq ss (ssadd))
  	(command "pline" (list 1.1 0.0) "w" 0 0 
                         (list 0.65 0.0) 
                         (list 0.65 5.0) 
                         (list 1.1 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 1.75 0.0) "w" 0 0 
                         (list 1.3 0.0) 
                         (list 1.3 5.0) 
                         (list 1.75 5.0) 
                         "c"
         )
  	(setq ent (entlast))
  	(ssadd ent ss)
        (command "pline" (list 1.95 0.0) "w" 0 0 
                         (list 2.15 0.0) 
                         (list 2.15 5.0) 
                         (list 1.95 5.0) 
                         "c"
         )
  	(setq ent (entlast))
  	(ssadd ent ss)
  	(command "move" ss "" "0,0" basepoint)
  )



(defun ins_hengxian(basepoint / ent ss)
  	(setq ss (ssadd))
  	(command "pline" (list 1.9 0.0) "w" 0 0 
                         (list 1.45 0.0) 
                         (list 1.45 5.0) 
                         (list 1.9 5.0) 
                         "c"
         )
  	(setq ent (entlast))
  	(ssadd ent ss)
        (command "pline" (list 1.05 0.0) "w" 0 0 
                         (list 1.25 0.0) 
                         (list 1.25 5.0) 
                         (list 1.05 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.55 0.0) "w" 0 0 
                         (list 2.1 0.0) 
                         (list 2.1 5.0) 
                         (list 2.55 5.0) 
                         "c"
         )
  	(setq ent (entlast))
  	(ssadd ent ss)
        (command "pline" (list 0.65 0.0) "w" 0 0 
                         (list 0.85 0.0) 
                         (list 0.85 5.0) 
                         (list 0.65 5.0) 
                         "c"
         )
  	(setq ent (entlast))
  	(ssadd ent ss)
  	(command "move" ss "" "0,0" basepoint)
  )

(defun ins_stop_start(basepoint / ent ss)
  	(setq ss (ssadd))
  	(command "pline" (list 0.65 0.0) "w" 0 0 
                         (list 0.85 0.0) 
                         (list 0.85 5.0) 
                         (list 0.65 5.0) 
                         "c"
         )
  	(setq ent (entlast))
  	(ssadd ent ss)
        (command "pline" (list 2.15 0.0) "w" 0 0 
                         (list 1.7 0.0) 
                         (list 1.7 5.0) 
                         (list 2.15 5.0) 
                         "c"
         )
  	(setq ent (entlast))
  	(ssadd ent ss)
        (command "pline" (list 0.0 0.0) "w" 0 0 
                         (list 0.2 0.0) 
                         (list 0.2 5.0) 
                         (list 0.0 5.0) 
                         "c"
         )
  	(setq ent (entlast))
  	(ssadd ent ss)
        (command "pline" (list 2.35 0.0) "w" 0 0 
                         (list 2.55 0.0) 
                         (list 2.55 5.0) 
                         (list 2.35 5.0) 
                         "c"
         )
  	(setq ent (entlast))
  	(ssadd ent ss)
        (command "pline" (list 1.5 0.0) "w" 0 0 
                         (list 1.05 0.0) 
                         (list 1.05 5.0) 
                         (list 1.5 5.0) 
                         "c"
         )
  	(setq ent (entlast))
  	(ssadd ent ss)
  	(command "move" ss "" "0,0" basepoint)
  )

(defun ins_str(strSub basepoint / x y base_txt);对输入的字符根据基点插入其barcode,并在其下写出文字.
  	(cond
  	    ((equal strSub "1")(ins_1 basepoint))
	    ((equal strSub "2")(ins_2 basepoint))
	    ((equal strSub "3")(ins_3 basepoint))
	    ((equal strSub "4")(ins_4 basepoint))
	    ((equal strSub "5")(ins_5 basepoint))
	    ((equal strSub "6")(ins_6 basepoint))
	    ((equal strSub "7")(ins_7 basepoint))
	    ((equal strSub "8")(ins_8 basepoint))
	    ((equal strSub "9")(ins_9 basepoint))
	    ((equal strSub "0")(ins_0 basepoint))
	    ((equal strSub "A")(ins_a basepoint))
	    ((equal strSub "B")(ins_b basepoint))
	    ((equal strSub "C")(ins_c basepoint))
	    ((equal strSub "D")(ins_d basepoint))
	    ((equal strSub "E")(ins_e basepoint))
	    ((equal strSub "F")(ins_f basepoint))
	    ((equal strSub "G")(ins_g basepoint))
	    ((equal strSub "H")(ins_h basepoint))
	    ((equal strSub "I")(ins_i basepoint))
	    ((equal strSub "J")(ins_j basepoint))
	    ((equal strSub "K")(ins_k basepoint))
	    ((equal strSub "L")(ins_l basepoint))
	    ((equal strSub "M")(ins_m basepoint))
	    ((equal strSub "N")(ins_n basepoint))
	    ((equal strSub "O")(ins_o basepoint))
	    ((equal strSub "P")(ins_p basepoint))
	    ((equal strSub "Q")(ins_q basepoint))
	    ((equal strSub "R")(ins_r basepoint))
	    ((equal strSub "S")(ins_s basepoint))
	    ((equal strSub "T")(ins_t basepoint))
	    ((equal strSub "U")(ins_u basepoint))
	    ((equal strSub "V")(ins_v basepoint))
	    ((equal strSub "W")(ins_w basepoint))
	    ((equal strSub "X")(ins_x basepoint))
	    ((equal strSub "Y")(ins_y basepoint))
	    ((equal strSub "Z")(ins_z basepoint))
	    ((equal strSub "-")(ins_hengxian basepoint))
	    ((equal strSub "*")(ins_stop_start basepoint))
	    ;(t (progn(print"\n错误,退出.")(exit)))
	)
	(setq x (car basepoint))
  	(setq y (cadr basepoint))
  	(setq base_txt(list (+ x 1.275)(- y 1.6)))
  	(command "text" "j" "mc" base_txt "1"  "0" strSub)
)


(defun c:cl04( / str size num_field stringlen cood_x cood_y startpoint
	         base_str endpoint strSub axis_x lbpoint len_x len_y
	      	 rtpoint num base_end)
  	(setvar"osmode" 0)
	(setvar"orthomode" 0)
  	
  	(setq str(getstring"\n请输入字符串:"))
	(setq str(strcase str))
  	(setq size(getstring"是六寸产品<6>还是五寸产品<5/Enter>:"))
  	(setq num_field(getint"\n共有几个区域?<Enter>:"))

  	(draw_6i2f);画6inch2fields周围图形.

  	(setq stringlen(strlen str));计算字符串的长度.
  	(if(equal stringlen 0)
	   (progn
	     (print"\n输入错误")
	     (exit)
	    )
	)
  	(setq cood_x (- 76.2 (/ (+ (* stringlen 2.55) (* 0.2 (- stringlen 1))) 2)));计算barcode左下基点
  	(setq cood_y (- 136.7 2.5))
  	(setq num 1);对字符串逐一取字符时的计数.
  
  	(setq startpoint(list (- cood_x 2.75) cood_y));插入起点barcode.
  	(ins_str "*" startpoint);(ins_stop_start startpoint)
  	(setq base_str (list (+ 2.55 (car startpoint))(- cood_y 1.6)));计算文字插入基点.
  	;(command "text" "j" "mr" base_str "1"  "0" "*")
  
  	(setq endpoint(list (+ 76.2 0.2 (/ (+ (* stringlen 2.55) (* 0.2 (- stringlen 1))) 2)) cood_y));插入终点barcode.
  	(ins_str "*" endpoint);(ins_stop_start endpoint)
  	(setq base_end(list(car endpoint)(- (cadr endpoint) 1.6)))
  	;(command "text" "j" "ml" base_end "1"  "0" "*")
  
  	(while(<= num stringlen);加中间的barcodes.
	      (setq strSub(substr str num 1))
	      (setq axis_x(+ cood_x (* (- num 1) 2.75)))
	      (setq basepoint (list axis_x cood_y))
	      (ins_str strSub basepoint)
	      (setq num (+ num 1))
	)
  	(setq lbpoint(list (- cood_x 6.25) cood_y));插入大长方形
  	(setq len_x (+ (- (* stringlen 2.75) 0.2) 12.5))
  	(setq len_y 5.0)
  	(setq rtpoint (list (+ (/ len_x 2) 76.2) (+ 136.7 2.5)))
  	(command "rectangle" lbpoint rtpoint)
  	(print"\n----->运行完毕.")
)

(print"\n-----------------为/cl04-pellicle/旧机器/6寸/而写,")
(print"\n-----输入cl04运行程序.Writer:Owal,2005-09-14.")


;(defun c:test( / basepoint);测试用,不做它用.
 ; 	(print"\n请点取基点:")
  ;	(setq basepoint (getpoint))
  ;	(ins_hengxian basepoint)
;)
