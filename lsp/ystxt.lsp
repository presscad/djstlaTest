(defun c:ystxt()
 (defun drw_su () 
        (command "pline" (list 24.4923 -55.118) "w" 0 0 
                         (list 32.4923 -55.118) 
                         (list 32.4923 -55.103) 
                         (list 24.4923 -55.103) 
                         "c"
         )
        (command "pline" (list 24.4923 -55.148) "w" 0 0 
                         (list 32.4923 -55.148) 
                         (list 32.4923 -55.133) 
                         (list 24.4923 -55.133) 
                         "c"
         )
        (command "pline" (list 16.7866 -54.9416) "w" 0 0 
                         (list 16.7994 -54.9158) 
                         (list 16.7892 -54.8825) 
                         (list 16.7223 -54.872) 
                         (list 16.7044 -54.8412) 
                         (list 16.7044 -54.7825) 
                         (list 16.6967 -54.7362) 
                         (list 16.6864 -54.6771) 
                         (list 16.6709 -54.6283) 
                         (list 16.6324 -54.5846) 
                         (list 16.5913 -54.5562) 
                         (list 16.5245 -54.5204) 
                         (list 16.4577 -54.505) 
                         (list 16.4268 -54.4946) 
                         (list 16.3574 -54.4896) 
                         (list 16.3112 -54.4816) 
                         (list 16.3035 -54.4791) 
                         (list 16.3446 -54.4741) 
                         (list 16.4011 -54.4691) 
                         (list 16.4808 -54.4587) 
                         (list 16.5476 -54.4433) 
                         (list 16.6247 -54.4175) 
                         (list 16.6915 -54.3737) 
                         (list 16.7223 -54.3329) 
                         (list 16.7532 -54.2558) 
                         (list 16.7403 -54.2016) 
                         (list 16.7018 -54.1583) 
                         (list 16.6529 -54.1275) 
                         (list 16.6496 -54.1258) 
                         (list 16.3539 -54.2716) 
                         (list 16.3554 -54.3612) 
                         (list 16.3451 -54.3921) 
                         (list 16.3348 -54.4046) 
                         (list 16.3066 -54.4304) 
                         (list 16.2809 -54.4354) 
                         (list 16.2526 -54.4408) 
                         (list 16.1832 -54.4433) 
                         (list 16.0162 -54.4383) 
                         (list 16.0008 -54.4254) 
                         (list 16.0059 -54.125) 
                         (list 16.0162 -54.1171) 
                         (list 16.2475 -54.1171) 
                         (list 16.2912 -54.1221) 
                         (list 16.3168 -54.1375) 
                         (list 16.3297 -54.1554) 
                         (list 16.3374 -54.1787) 
                         (list 16.3451 -54.1941) 
                         (list 16.3528 -54.2096) 
                         (list 16.3539 -54.2716) 
                         (list 16.6496 -54.1258) 
                         (list 16.5759 -54.0966) 
                         (list 16.5527 -54.0887) 
                         (list 16.4242 -54.0733) 
                         (list 16.3652 -54.0733) 
                         (list 16.2598 -54.0633) 
                         (list 16.0722 -54.0579) 
                         (list 15.5223 -54.0633) 
                         (list 15.5018 -54.0658) 
                         (list 15.4992 -54.1121) 
                         (list 15.5223 -54.1171) 
                         (list 15.6508 -54.1196) 
                         (list 15.6585 -54.8825) 
                         (list 15.53 -54.88) 
                         (list 15.5326 -54.7541) 
                         (list 15.5326 -54.7208) 
                         (list 15.5429 -54.7154) 
                         (list 15.5377 -54.6437) 
                         (list 15.5198 -54.6383) 
                         (list 15.4683 -54.6358) 
                         (list 15.4427 -54.7) 
                         (list 15.4118 -54.7566) 
                         (list 15.3604 -54.8079) 
                         (list 15.3219 -54.8412) 
                         (list 15.2885 -54.8541) 
                         (list 15.2294 -54.867) 
                         (list 15.1703 -54.8875) 
                         (list 15.0546 -54.8875) 
                         (list 14.8444 -54.885) 
                         (list 14.8316 -54.8695) 
                         (list 14.829 -54.5125) 
                         (list 14.883 -54.5254) 
                         (list 14.9421 -54.5358) 
                         (list 15.0089 -54.5487) 
                         (list 15.068 -54.5691) 
                         (list 15.0886 -54.6) 
                         (list 15.104 -54.6308) 
                         (list 15.1066 -54.6821) 
                         (list 15.1194 -54.69) 
                         (list 15.1862 -54.6925) 
                         (list 15.1913 -54.6821) 
                         (list 15.1888 -54.3046) 
                         (list 15.1759 -54.2996) 
                         (list 15.1143 -54.3021) 
                         (list 15.1014 -54.3096) 
                         (list 15.0963 -54.3429) 
                         (list 15.0911 -54.3687) 
                         (list 15.0808 -54.3971) 
                         (list 15.0552 -54.4125) 
                         (list 15.0269 -54.4354) 
                         (list 15.0141 -54.4458) 
                         (list 14.9601 -54.4508) 
                         (list 14.9241 -54.4537) 
                         (list 14.8316 -54.4537) 
                         (list 14.8316 -54.1171) 
                         (list 14.9575 -54.1146) 
                         (list 15.0269 -54.1196) 
                         (list 15.1297 -54.1196) 
                         (list 15.1811 -54.13) 
                         (list 15.2273 -54.1404) 
                         (list 15.2633 -54.1554) 
                         (list 15.2967 -54.1837) 
                         (list 15.3353 -54.2275) 
                         (list 15.3609 -54.2533) 
                         (list 15.3866 -54.2866) 
                         (list 15.4098 -54.3021) 
                         (list 15.4432 -54.3071) 
                         (list 15.4766 -54.3021) 
                         (list 15.4766 -54.2608) 
                         (list 15.4766 -54.0633) 
                         (list 14.3434 -54.0658) 
                         (list 14.3382 -54.0787) 
                         (list 14.3408 -54.1096) 
                         (list 14.3511 -54.125) 
                         (list 14.4796 -54.125) 
                         (list 14.4796 -54.88) 
                         (list 14.3254 -54.885) 
                         (list 14.3202 -54.9029) 
                         (list 14.3177 -54.9337) 
                         (list 14.3382 -54.9391) 
                         (list 16.1858 -54.9337) 
                         (list 16.1935 -54.9237) 
                         (list 16.191 -54.8875) 
                         (list 16.1832 -54.88) 
                         (list 16.0162 -54.8775) 
                         (list 16.0085 -54.505) 
                         (list 16.0162 -54.4971) 
                         (list 16.1087 -54.5025) 
                         (list 16.1601 -54.5075) 
                         (list 16.1987 -54.5204) 
                         (list 16.2397 -54.5408) 
                         (list 16.2629 -54.5612) 
                         (list 16.286 -54.6025) 
                         (list 16.2989 -54.6258) 
                         (list 16.304 -54.6666) 
                         (list 16.3117 -54.7258) 
                         (list 16.3143 -54.7745) 
                         (list 16.3323 -54.8387) 
                         (list 16.3605 -54.867) 
                         (list 16.4017 -54.9004) 
                         (list 16.4607 -54.9262) 
                         (list 16.5301 -54.9441) 
                         (list 16.5687 -54.9516) 
                         (list 16.7845 -54.9466) 
                         "c"
         )
        (command "pline" (list 13.2197 -54.0708) "w" 0 0 
                         (list 13.2223 -54.1221) 
                         (list 13.2762 -54.125) 
                         (list 13.3045 -54.13) 
                         (list 13.3071 -54.8825) 
                         (list 13.2994 -54.8929) 
                         (list 13.1503 -54.8929) 
                         (list 13.1452 -54.9029) 
                         (list 13.1452 -54.9362) 
                         (list 13.158 -54.9441) 
                         (list 13.176 -54.9491) 
                         (list 13.8364 -54.9466) 
                         (list 13.8519 -54.9362) 
                         (list 13.8544 -54.9004) 
                         (list 13.839 -54.885) 
                         (list 13.6617 -54.8825) 
                         (list 13.6591 -54.5871) 
                         (list 13.6643 -54.5587) 
                         (list 13.672 -54.5487) 
                         (list 13.6977 -54.5487) 
                         (list 13.7311 -54.5458) 
                         (list 13.7594 -54.5458) 
                         (list 13.8698 -54.5433) 
                         (list 13.9572 -54.5408) 
                         (list 14.0523 -54.5433) 
                         (list 14.1088 -54.5304) 
                         (list 14.1987 -54.515) 
                         (list 14.2681 -54.4896) 
                         (list 14.3375 -54.4483) 
                         (list 14.3786 -54.4075) 
                         (list 14.4069 -54.3612) 
                         (list 14.4095 -54.3304) 
                         (list 14.4146 -54.2866) 
                         (list 14.3992 -54.2404) 
                         (list 14.3812 -54.2016) 
                         (list 14.3529 -54.1658) 
                         (list 14.2938 -54.135) 
                         (list 14.2424 -54.1096) 
                         (list 14.1808 -54.0966) 
                         (list 14.1139 -54.0887) 
                         (list 14.0824 -54.0866) 
                         (list 13.654 -54.1275) 
                         (list 13.7671 -54.125) 
                         (list 13.8313 -54.1196) 
                         (list 13.9109 -54.125) 
                         (list 13.9701 -54.1454) 
                         (list 13.9983 -54.1787) 
                         (list 14.0163 -54.22) 
                         (list 14.024 -54.2662) 
                         (list 14.0214 -54.3225) 
                         (list 14.0266 -54.3687) 
                         (list 14.0163 -54.41) 
                         (list 14.0163 -54.42) 
                         (list 13.988 -54.4691) 
                         (list 13.9572 -54.4846) 
                         (list 13.9367 -54.4896) 
                         (list 13.875 -54.4896) 
                         (list 13.6617 -54.4896) 
                         (list 13.6617 -54.4816) 
                         (list 13.654 -54.1275) 
                         (list 14.0824 -54.0866) 
                         (list 14.0343 -54.0837) 
                         (list 13.9624 -54.0733) 
                         (list 13.8775 -54.0708) 
                         (list 13.7876 -54.0658) 
                         "c"
         )
        (command "pline" (list 17.7271 -54.8745) "w" 0 0 
                         (list 17.7065 -54.88) 
                         (list 17.7091 -54.9208) 
                         (list 17.7348 -54.9262) 
                         (list 18.3875 -54.9262) 
                         (list 18.4054 -54.9158) 
                         (list 18.4054 -54.8745) 
                         (list 18.372 -54.8695) 
                         (list 18.2255 -54.8695) 
                         (list 18.2178 -54.1096) 
                         (list 18.3695 -54.1121) 
                         (list 18.3952 -54.0966) 
                         (list 18.3977 -54.0633) 
                         (list 18.3875 -54.0529) 
                         (list 18.3643 -54.0479) 
                         (list 17.835 -54.0504) 
                         (list 17.6011 -54.5254) 
                         (list 17.5908 -54.5333) 
                         (list 17.3493 -54.0529) 
                         (list 16.7712 -54.0554) 
                         (list 16.766 -54.1041) 
                         (list 16.7892 -54.1146) 
                         (list 16.9433 -54.1146) 
                         (list 16.9459 -54.8233) 
                         (list 16.9407 -54.8466) 
                         (list 16.9279 -54.872) 
                         (list 16.8894 -54.8775) 
                         (list 16.8508 -54.885) 
                         (list 16.8508 -54.9158) 
                         (list 16.8559 -54.9262) 
                         (list 17.2029 -54.9312) 
                         (list 17.2157 -54.9208) 
                         (list 17.2157 -54.8929) 
                         (list 17.2054 -54.8775) 
                         (list 17.0615 -54.8745) 
                         (list 17.0461 -54.8516) 
                         (list 17.0358 -54.8258) 
                         (list 17.0281 -54.1529) 
                         (list 17.0358 -54.1554) 
                         (list 17.393 -54.9029) 
                         (list 17.4136 -54.9262) 
                         (list 17.4932 -54.9237) 
                         (list 17.8581 -54.1658) 
                         (list 17.871 -54.1454) 
                         (list 17.8812 -54.1737) 
                         (list 17.8838 -54.862) 
                         (list 17.8812 -54.872) 
                         (list 17.7451 -54.8745) 
                         "c"
         )
        (command "pline" (list 10.6488 -53.8021) "w" 0 0 
                         (list 10.6618 -53.8121) 
                         (list 10.7072 -53.7958) 
                         (list 11.6034 -53.4192) 
                         (list 11.5612 -53.4096) 
                         (list 11.5158 -53.4096) 
                         (list 10.7949 -53.7112) 
                         (list 10.7916 -53.7341) 
                         (list 10.6423 -53.7958) 
                         "c"
         )
        (command "pline" (list 10.4799 -53.9971) "w" 0 0 
                         (list 10.5059 -54.0004) 
                         (list 11.8178 -53.4421) 
                         (list 11.7593 -53.4258) 
                         (list 11.6846 -53.4292) 
                         (list 11.545 -53.4937) 
                         (list 11.5547 -53.5071) 
                         (list 10.8209 -53.8121) 
                         (list 10.8176 -53.8379) 
                         (list 10.4799 -53.9841) 
                         "c"
         )
        (command "pline" (list 10.376 -54.1591) "w" 0 0 
                         (list 10.4312 -54.1462) 
                         (list 11.9931 -53.4808) 
                         (list 11.9411 -53.4646) 
                         (list 11.8794 -53.4583) 
                         (list 11.8632 -53.4612) 
                         (list 11.571 -53.5912) 
                         (list 11.5515 -53.6367) 
                         (list 10.8176 -53.9387) 
                         (list 10.7429 -53.9841) 
                         (list 10.3857 -54.1366) 
                         (list 10.3695 -54.1529) 
                         "c"
         )
        (command "pline" (list 10.3111 -54.3054) "w" 0 0 
                         (list 10.3533 -54.3054) 
                         (list 10.402 -54.2925) 
                         (list 12.123 -53.5362) 
                         (list 12.0711 -53.52) 
                         (list 12.0224 -53.52) 
                         (list 11.5612 -53.7179) 
                         (list 11.5612 -53.7437) 
                         (list 10.8209 -54.0521) 
                         (list 10.8079 -54.0683) 
                         (list 10.7689 -54.0912) 
                         (list 10.3013 -54.2954) 
                         "c"
         )
        (command "pline" (list 10.2818 -54.445) "w" 0 0 
                         (list 12.2399 -53.6108) 
                         (list 12.2107 -53.5817) 
                         (list 12.162 -53.5783) 
                         (list 12.136 -53.5846) 
                         (list 11.6067 -53.8216) 
                         (list 11.5807 -53.8379) 
                         (list 11.5677 -53.8671) 
                         (list 10.8371 -54.1691) 
                         (list 10.8273 -54.1883) 
                         (list 10.2688 -54.4254) 
                         "c"
         )
        (command "pline" (list 10.2493 -54.5716) "w" 0 0 
                         (list 10.2916 -54.5746) 
                         (list 12.3406 -53.6821) 
                         (list 12.3081 -53.6596) 
                         (list 12.2561 -53.6562) 
                         (list 11.571 -53.9483) 
                         (list 11.5872 -53.9741) 
                         (list 10.8371 -54.2791) 
                         (list 10.8209 -54.2987) 
                         (list 10.7819 -54.3216) 
                         (list 10.2526 -54.5521) 
                         "c"
         )
        (command "pline" (list 10.2591 -54.6916) "w" 0 0 
                         (list 12.4477 -53.7666) 
                         (list 12.412 -53.7341) 
                         (list 12.3763 -53.7179) 
                         (list 11.5677 -54.0683) 
                         (list 11.5904 -54.0846) 
                         (list 10.8631 -54.3962) 
                         (list 10.8241 -54.4254) 
                         (list 10.2428 -54.6787) 
                         "c"
         )
        (command "pline" (list 10.4247 -55.4066) "w" 0 0 
                         (list 10.4539 -55.3841) 
                         (list 11.3697 -54.9945) 
                         (list 11.3794 -55.0075) 
                         (list 11.3664 -55.0237) 
                         (list 11.256 -55.0691) 
                         (list 11.1975 -55.095) 
                         (list 11.1943 -55.1212) 
                         (list 10.9735 -55.2087) 
                         (list 10.9508 -55.2054) 
                         (list 10.954 -55.2216) 
                         (list 10.98 -55.2312) 
                         (list 10.9085 -55.2379) 
                         (list 10.5026 -55.41) 
                         "c"
         )
        (command "pline" (list 10.1746 -55.387) "w" 0 0 
                         (list 11.4833 -54.8287) 
                         (list 11.493 -54.8191) 
                         (list 11.5255 -54.8129) 
                         (list 11.5223 -54.832) 
                         (list 11.5125 -54.8516) 
                         (list 11.1975 -54.9816) 
                         (list 11.1878 -55.017) 
                         (list 10.691 -55.2216) 
                         (list 10.6812 -55.225) 
                         (list 10.7072 -55.2379) 
                         (list 10.6293 -55.2379) 
                         (list 10.4831 -55.2962) 
                         (list 10.4572 -55.2995) 
                         (list 10.4474 -55.3225) 
                         (list 10.4442 -55.345) 
                         (list 10.3078 -55.4033) 
                         (list 10.2461 -55.4033) 
                         "c"
         )
        (command "pline" (list 10.0253 -55.3354) "w" 0 0 
                         (list 11.6164 -54.6633) 
                         (list 11.6229 -54.6762) 
                         (list 11.6294 -54.6891) 
                         (list 11.1748 -54.8745) 
                         (list 11.1683 -54.8875) 
                         (list 10.678 -55.095) 
                         (list 10.4344 -55.1958) 
                         (list 10.4312 -55.2087) 
                         (list 10.4312 -55.225) 
                         (list 10.4409 -55.2379) 
                         (list 10.376 -55.2445) 
                         (list 10.1292 -55.3612) 
                         (list 10.0837 -55.3708) 
                         (list 10.0643 -55.3645) 
                         "c"
         )
        (command "pline" (list 9.87914 -55.2766) "w" 0 0 
                         (list 11.6749 -54.5141) 
                         (list 11.6846 -54.5175) 
                         (list 11.6944 -54.5271) 
                         (list 11.6879 -54.5433) 
                         (list 11.1845 -54.7512) 
                         (list 11.178 -54.7641) 
                         (list 10.4377 -55.0754) 
                         (list 10.4409 -55.095) 
                         (list 10.2104 -55.202) 
                         (list 10.1584 -55.212) 
                         (list 10.1487 -55.2216) 
                         (list 10.1779 -55.2283) 
                         (list 10.1649 -55.2412) 
                         (list 10.1227 -55.2379) 
                         (list 10.1162 -55.2379) 
                         (list 10.0026 -55.2929) 
                         (list 9.9311 -55.3091) 
                         (list 9.88564 -55.28) 
                         "c"
         )
        (command "pline" (list 9.77198 -55.212) "w" 0 0 
                         (list 11.6879 -54.3875) 
                         (list 11.7106 -54.3841) 
                         (list 11.7236 -54.3941) 
                         (list 11.1651 -54.6375) 
                         (list 11.1683 -54.6571) 
                         (list 10.4344 -54.9587) 
                         (list 10.4377 -54.9879) 
                         (list 9.89539 -55.2183) 
                         (list 9.90839 -55.2312) 
                         (list 9.83694 -55.2412) 
                         (list 9.80773 -55.2379) 
                         "c"
         )
        (command "pline" (list 9.70706 -55.1795) "w" 0 0 
                         (list 9.66806 -55.147) 
                         (list 9.66161 -55.1404) 
                         (list 11.7171 -54.2575) 
                         (list 11.7431 -54.2575) 
                         (list 11.7528 -54.2771) 
                         (list 11.243 -54.4912) 
                         (list 11.1651 -54.5175) 
                         (list 11.1651 -54.5466) 
                         (list 10.4182 -54.8483) 
                         (list 10.4182 -54.8745) 
                         "c"
         )
        (command "pline" (list 9.5804 -55.0691) "w" 0 0 
                         (list 11.7398 -54.1312) 
                         (list 11.7528 -54.1504) 
                         (list 11.7398 -54.1637) 
                         (list 11.1586 -54.4104) 
                         (list 11.1553 -54.4362) 
                         (list 10.4214 -54.735) 
                         (list 10.4085 -54.767) 
                         (list 9.61611 -55.0983) 
                         "c"
         )
        (command "pline" (list 11.8527 -54.0812) "w" 0 0 
                         (list 11.8964 -54.0733) 
                         (list 12.5156 -54.0708) 
                         (list 12.5439 -54.0887) 
                         (list 12.5413 -54.1275) 
                         (list 12.5311 -54.1325) 
                         (list 12.3615 -54.1325) 
                         (list 12.3615 -54.6771) 
                         (list 12.3666 -54.7104) 
                         (list 12.3743 -54.767) 
                         (list 12.3897 -54.7979) 
                         (list 12.4051 -54.8466) 
                         (list 12.4488 -54.8825) 
                         (list 12.5105 -54.9004) 
                         (list 12.5593 -54.9029) 
                         (list 12.6416 -54.9083) 
                         (list 12.7058 -54.9029) 
                         (list 12.7752 -54.8954) 
                         (list 12.8266 -54.8825) 
                         (list 12.8831 -54.862) 
                         (list 12.9268 -54.8183) 
                         (list 12.9525 -54.7641) 
                         (list 12.9576 -54.7387) 
                         (list 12.9602 -54.6691) 
                         (list 12.9576 -54.5254) 
                         (list 12.9576 -54.1683) 
                         (list 12.9525 -54.1454) 
                         (list 12.937 -54.135) 
                         (list 12.9293 -54.13) 
                         (list 12.8189 -54.135) 
                         (list 12.7906 -54.1221) 
                         (list 12.7906 -54.0758) 
                         (list 12.8112 -54.0733) 
                         (list 13.1452 -54.0683) 
                         (list 13.1529 -54.0912) 
                         (list 13.1529 -54.1196) 
                         (list 13.1144 -54.1325) 
                         (list 13.0758 -54.1375) 
                         (list 13.063 -54.1583) 
                         (list 13.0578 -54.1787) 
                         (list 13.0553 -54.2046) 
                         (list 13.063 -54.7258) 
                         (list 13.0553 -54.7745) 
                         (list 13.0398 -54.8054) 
                         (list 13.0167 -54.8441) 
                         (list 12.991 -54.8745) 
                         (list 12.955 -54.8954) 
                         (list 12.8857 -54.9237) 
                         (list 12.8266 -54.9441) 
                         (list 12.77 -54.957) 
                         (list 12.7469 -54.962) 
                         (list 12.418 -54.97) 
                         (list 12.3872 -54.9645) 
                         (list 12.3126 -54.9545) 
                         (list 12.2458 -54.9416) 
                         (list 12.1636 -54.9183) 
                         (list 12.1225 -54.8954) 
                         (list 12.0916 -54.885) 
                         (list 12.0685 -54.862) 
                         (list 12.0531 -54.8337) 
                         (list 12.0351 -54.8004) 
                         (list 12.0223 -54.7516) 
                         (list 12.0146 -54.6796) 
                         (list 12.0146 -54.6) 
                         (list 12.0146 -54.1583) 
                         (list 12.0069 -54.135) 
                         (list 11.994 -54.1325) 
                         (list 11.8527 -54.135) 
                         (list 11.8476 -54.1146) 
                         "c"
         )
        (command "pline" (list 18.5627 -54.9262) "w" 0 0 
                         (list 18.9841 -54.9237) 
                         (list 19.6368 -54.3921) 
                         (list 19.4826 -54.8412) 
                         (list 19.4261 -54.9183) 
                         (list 19.8167 -54.9262) 
                         (list 20.0968 -54.0196) 
                         (list 19.7011 -54.0246) 
                         (list 18.6141 -54.8929) 
                         (list 18.5627 -54.9133) 
                         "c"
         )
        (command "pline" (list 20.2054 -54.6616) "w" 0 0 
                         (list 20.19 -54.6871) 
                         (list 20.1926 -54.9108) 
                         (list 20.2183 -54.9262) 
                         (list 20.2953 -54.9262) 
                         (list 20.3262 -54.9054) 
                         (list 20.3724 -54.8825) 
                         (list 20.4084 -54.9004) 
                         (list 20.488 -54.9208) 
                         (list 20.5831 -54.9362) 
                         (list 20.6962 -54.9391) 
                         (list 20.8118 -54.9362) 
                         (list 20.8992 -54.9183) 
                         (list 21.0071 -54.8695) 
                         (list 21.0894 -54.8029) 
                         (list 21.1227 -54.7695) 
                         (list 21.1433 -54.7129) 
                         (list 21.1562 -54.6437) 
                         (list 21.1536 -54.5666) 
                         (list 21.1202 -54.5025) 
                         (list 21.0996 -54.4637) 
                         (list 21.0585 -54.4354) 
                         (list 21.002 -54.4046) 
                         (list 20.9275 -54.3791) 
                         (list 20.8478 -54.3558) 
                         (list 20.7707 -54.3379) 
                         (list 20.7065 -54.3279) 
                         (list 20.6371 -54.315) 
                         (list 20.5806 -54.3021) 
                         (list 20.5086 -54.2916) 
                         (list 20.4598 -54.2737) 
                         (list 20.4084 -54.2633) 
                         (list 20.3853 -54.2508) 
                         (list 20.3673 -54.2275) 
                         (list 20.3673 -54.2016) 
                         (list 20.3698 -54.1812) 
                         (list 20.3801 -54.1554) 
                         (list 20.411 -54.1325) 
                         (list 20.4521 -54.1121) 
                         (list 20.4855 -54.1016) 
                         (list 20.5189 -54.0966) 
                         (list 20.5575 -54.0837) 
                         (list 20.6191 -54.0837) 
                         (list 20.6808 -54.0837) 
                         (list 20.7553 -54.0941) 
                         (list 20.817 -54.1196) 
                         (list 20.8684 -54.1375) 
                         (list 20.912 -54.1941) 
                         (list 20.9455 -54.2429) 
                         (list 20.9686 -54.2737) 
                         (list 20.9917 -54.2841) 
                         (list 21.0457 -54.2841) 
                         (list 21.0508 -54.2687) 
                         (list 21.0508 -54.0479) 
                         (list 21.0302 -54.0375) 
                         (list 20.9635 -54.0425) 
                         (list 20.9429 -54.0658) 
                         (list 20.9198 -54.0733) 
                         (list 20.9018 -54.0733) 
                         (list 20.8761 -54.0733) 
                         (list 20.8427 -54.0579) 
                         (list 20.7605 -54.035) 
                         (list 20.6782 -54.0271) 
                         (list 20.6063 -54.0246) 
                         (list 20.5369 -54.0271) 
                         (list 20.4624 -54.04) 
                         (list 20.3904 -54.0708) 
                         (list 20.3288 -54.0966) 
                         (list 20.2953 -54.13) 
                         (list 20.2517 -54.1708) 
                         (list 20.2208 -54.22) 
                         (list 20.1977 -54.2916) 
                         (list 20.2054 -54.3533) 
                         (list 20.2208 -54.42) 
                         (list 20.2568 -54.4587) 
                         (list 20.2928 -54.4816) 
                         (list 20.3621 -54.515) 
                         (list 20.4598 -54.5487) 
                         (list 20.542 -54.5691) 
                         (list 20.6088 -54.5766) 
                         (list 20.6654 -54.5796) 
                         (list 20.7348 -54.5896) 
                         (list 20.8067 -54.6025) 
                         (list 20.8838 -54.6229) 
                         (list 20.93 -54.6512) 
                         (list 20.9635 -54.6871) 
                         (list 20.9814 -54.7208) 
                         (list 20.9789 -54.772) 
                         (list 20.9429 -54.8233) 
                         (list 20.8992 -54.8441) 
                         (list 20.8504 -54.8695) 
                         (list 20.8041 -54.88) 
                         (list 20.7553 -54.8825) 
                         (list 20.6962 -54.89) 
                         (list 20.6294 -54.8875) 
                         (list 20.5729 -54.8775) 
                         (list 20.4829 -54.8595) 
                         (list 20.4316 -54.8258) 
                         (list 20.3827 -54.7925) 
                         (list 20.339 -54.7487) 
                         (list 20.3031 -54.7) 
                         (list 20.2876 -54.6721) 
                         "c"
         )
        (command "pline" (list 21.9759 -54.0296) "w" 0 0 
                         (list 22.4872 -54.0271) 
                         (list 22.4898 -54.0758) 
                         (list 22.3511 -54.0862) 
                         (list 22.2765 -54.0941) 
                         (list 21.9219 -54.3354) 
                         (list 22.4513 -54.8441) 
                         (list 22.4975 -54.8541) 
                         (list 22.6363 -54.8541) 
                         (list 22.644 -54.9029) 
                         (list 21.9117 -54.9108) 
                         (list 21.9065 -54.8516) 
                         (list 22.035 -54.8491) 
                         (list 21.6469 -54.4816) 
                         (list 21.6444 -54.4921) 
                         (list 21.6367 -54.5025) 
                         (list 21.6444 -54.8441) 
                         (list 21.6598 -54.8595) 
                         (list 21.8063 -54.8595) 
                         (list 21.8114 -54.8979) 
                         (list 21.7986 -54.9083) 
                         (list 21.1227 -54.9133) 
                         (list 21.1176 -54.8954) 
                         (list 21.1176 -54.8645) 
                         (list 21.1407 -54.8595) 
                         (list 21.2795 -54.8516) 
                         (list 21.2718 -54.0966) 
                         (list 21.1536 -54.0941) 
                         (list 21.1176 -54.0912) 
                         (list 21.1125 -54.045) 
                         (list 21.1459 -54.0375) 
                         (list 21.8012 -54.0325) 
                         (list 21.8012 -54.0787) 
                         (list 21.7909 -54.0912) 
                         (list 21.6469 -54.0941) 
                         (list 21.6367 -54.1171) 
                         (list 21.6367 -54.4279) 
                         (list 21.6495 -54.4383) 
                         (list 22.1378 -54.1066) 
                         (list 22.1275 -54.0837) 
                         (list 22.0016 -54.0887) 
                         (list 21.9682 -54.0812) 
                         (list 21.9682 -54.04) 
                         "c"
         )
  )
  (drw_su)
  (setq txt (getstring T "光罩光称及台头:"))
  (setq txt_dt (list (cons 0 "text")(cons 1 txt) (cons 10 '(-30 -55.54 0))(cons 40 2.0)))
  (entmake txt_dt)
  (setq c_date (getvar "CDATE"))
  (setq txt (itoa (fix c_date)))
  (setq txt (strcat (substr txt 1 4) "/" (substr txt 5 2) "/" (substr txt 7 2)))
  (setq txt_dt (list (cons 0 "text")(cons 1 txt) (cons 10 '(24.5 -54.9 0))(cons 40 1.0)))
  (entmake txt_dt)
)
(prompt "输入ystxt运行")
