(defun c:expblk ()
  (setvar "osmode" 0)
  (setvar "orthomode" 0)
  (command "zoom" "e")    
  (command "layer" "U" "*" "")
  (vl-load-com)					
  (setq exp_ss (ssget "x" (list (cons 0 "insert"))))
  (while exp_ss
    (setq sum_cnt (sslength exp_ss))
    (setq cnt 0)
    (while (< cnt sum_cnt)      
      (setq ent_name (ssname exp_ss cnt))      
      (setq blk_obj (vlax-ename->vla-object ent_name))
      (setq ly (vla-get-layer blk_obj))
      (vlax-invoke blk_obj 'explode)	
      (vlax-invoke blk_obj 'delete)
      (vlax-release-object blk_obj)
      (setq cnt (1+ cnt))
    )
    (setq exp_ss (ssget "x" (list (cons 0 "insert"))))
  )
  (prompt "全部的块都被炸开，注意炸开后的物体可能放错层!")
)
(prompt "expblk炸开后的图形可能所在的层不是块所在的层，请注意！")
