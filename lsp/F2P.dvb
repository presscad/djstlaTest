Attribute VB_Name = "模块1"

Public Sub f2p()
ZoomAll
Dim i As Integer
i = 0
Dim ssface As AcadSelectionSet
If ThisDrawing.SelectionSets.Count <> 0 Then
For i = 0 To ThisDrawing.SelectionSets.Count - 1
Set ssface = ThisDrawing.SelectionSets.Item(i)
ssface.Delete
Next
End If
Set ssface = ThisDrawing.SelectionSets.Add("ssface")
Dim filtertype(1) As Integer
Dim filterdata(1) As Variant
filtertype(0) = 100
filtertype(1) = 0
filterdata(0) = "AcDbEntity"
filterdata(1) = "3dface"
ssface.Select acSelectionSetAll, , , filtertype, filterdata
If ssface.Count <> 0 Then
MsgBox ("图形中face的数量为：" & ssface.Count)
Dim newlay As AcadLayer
Set newlay = ThisDrawing.Layers.Add("face2pl")
ThisDrawing.ActiveLayer = newlay
newlay.color = acGreen
Dim plobj As AcadLWPolyline
For i = 0 To ssface.Count - 1
Dim pt As Variant
Dim pt1(0 To 9) As Double
pt = ssface.Item(i).Coordinates
pt1(0) = pt(0): pt1(1) = pt(1):
pt1(2) = pt(3): pt1(3) = pt(4):
pt1(4) = pt(6): pt1(5) = pt(7):
pt1(6) = pt(9): pt1(7) = pt(10):
pt1(8) = pt(0): pt1(9) = pt(1):
Set plobj = ThisDrawing.ModelSpace.AddLightWeightPolyline(pt1)
Next
ThisDrawing.SendCommand "regen" & vbCr
ZoomAll
Else
MsgBox "图形中没3DFACE！！！"
End If
End Sub

Attribute VB_Name = "模块11"

Public Sub xmb()
Dim setvarname As String
Dim setvardata As Integer
setvarname = "osmode"
setvardata = 0
Call ThisDrawing.SetVariable(setvarname, setvardata)
setvarname = "orthomode"
setvardata = 0
Call ThisDrawing.SetVariable(setvarname, setvardata)
Dim ss_m_blks As AcadSelectionSet
If ThisDrawing.SelectionSets.Count <> 0 Then
For i = 0 To ThisDrawing.SelectionSets.Count - 1
Set ss_m_blks = ThisDrawing.SelectionSets.Item(i)
ss_m_blks.Delete
Next
End If
Set ss_m_blks = ThisDrawing.SelectionSets.Add("mblk")
Dim filtertype(1) As Integer
Dim filterdata(1) As Variant
filtertype(0) = 100
filtertype(1) = 0
filterdata(0) = "AcDbMInsertBlock"
filterdata(1) = "insert"
ss_m_blks.Select acSelectionSetAll, , , filtertype, filterdata
MsgBox ("图形中块的数量为：" & ss_m_blks.Count)
If ss_m_blks.Count <> 0 Then
For i = 0 To ss_m_blks.Count - 1
Dim blk As AcadBlockReference
Set blk = ss_m_blks.Item(i)
Dim blknew As AcadBlockReference
blknew_name% = blk.Name
blknew_int = blk.InsertionPoint
blknew_xscale# = blk.XScaleFactor
blknew_yscale# = blk.YScaleFactor
blknew_zscale# = blk.ZScaleFactor
blknew_rotation# = blk.Rotation
blknew_y% = blk.Columns
blknew_ydata# = blk.ColumnSpacing
blknew_x% = blk.Rows
blknew_xdata# = blk.RowSpacing
Set blknew = ThisDrawing.ModelSpace.InsertBlock(blknew_int, blknew_name, blknew_xscale _
             , blknew_yscale, blknew_xscale, blknew_rotation)
ss_m_blks.Item(i).Erase
Dim blkarr As Variant
blkarr = blknew.ArrayRectangular(blknew_x, blknew_y, 1, blknew_xdata, blknew_ydata, 1)
Next
End If
Call xb
End Sub

Public Sub xb()
Dim setvarname As String
Dim setvardata As Variant
setvarname = "osmode"
setvardata = 0
Call ThisDrawing.SetVariable(setvarname, setvardata)
setvarname = "orthomode"
setvardata = 0
Call ThisDrawing.SetVariable(setvarname, setvardata)
Dim i As Double
Dim ss As AcadSelectionSet
If ThisDrawing.SelectionSets.Count <> 0 Then
   For i = 0 To ThisDrawing.SelectionSets.Count - 1
   Set ss = ThisDrawing.SelectionSets.Item(i)
   ss.Delete
   Next
End If
Set ss = ThisDrawing.SelectionSets.Add("temp")
Dim filtertype(0 To 1) As Integer
Dim filterdata(0 To 1) As Variant
filtertype(0) = 100
filterdata(0) = "AcDbBlockReference"
filtertype(1) = 0
filterdata(1) = "insert"
ss.Select acSelectionSetAll, , , filtertype, filterdata
If ss.Count <> 0 Then
Dim blockref As AcadBlockReference
Dim blkobj As Variant
Dim ss_num As Double
ss_num = ss.Count - 1
 For i = 0 To ss_num
  Set blockref = ss.Item(i)
  blkobj = blockref.Explode
  blockref.Delete
 Next
 Else
 End If
 MsgBox ("图形中块的数量为：" & ss.Count)
End Sub
