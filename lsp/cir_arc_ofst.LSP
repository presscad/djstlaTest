(defun get_dt_vl (item dt)
  (cdr (assoc item dt))
)

(defun c:cofst ()
    (Setq FLTR (list
		 (cons 0 "arc")
		 )
    )
    (setq ss (ssget "x" FLTR))
    (setq rad_add (getreal "input the radius add"))
    (if	(/= ss nil)
      (progn
	(setq cnt_all (sslength ss))
	(setq cnt 0)
	(while (< cnt cnt_all)
	  (setq ent_name (ssname ss cnt))
	  (setq l_dt (entget ent_name))
	  (setq rad (get_dt_vl 40 l_dt))
	  (setq rad (+ rad rad_add))
	      (setq l_dt (subst	(cons 40 rad)
				(assoc 40 l_dt)
				l_dt
			 )
		)
	  (entmake l_dt)
	  (setq cnt (1+ cnt))
	)
      )
    )
    (Setq FLTR (list
		 (cons 0 "circle")
		 )
    )
  (setq ss (ssget "x" FLTR))
    (if	(/= ss nil)
      (progn
	(setq cnt_all (sslength ss))
	(setq cnt 0)
	(while (< cnt cnt_all)
	  (setq ent_name (ssname ss cnt))
	  (setq l_dt (entget ent_name))
	  (setq rad (get_dt_vl 40 l_dt))
	  (setq rad (+ rad rad_add))
	      (setq l_dt (subst	(cons 40 rad)
				(assoc 40 l_dt)
				l_dt
			 )
		)	    
	  (entmake l_dt)
	  (setq cnt (1+ cnt))
	)
      )
    )
  )

  (prompt "input cofst to run(缩小输入负值，放大输入正值)")
