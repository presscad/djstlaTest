(defun c:myoff ()
  (setq off (getreal "输入偏移距离:"))
  (setq nn 0)
  ;;;(setq pt2 (getpoint "Enter a point："))
  (progn (setq ss (ssget))
	 (setq len (sslength ss))
	 (setq n 1)
	 (while	(<= n len)
	   (setq en1 (ssname ss (1- n)))
	   (setq a (entget en1))
	   (setq a (cdr (assoc 0 a)))
	   (print a)
	   ;;(if (= "LWPOLYLINE" a)
	   (command "offset" off en1 "@1,1" "") (setq nn (1+ nn))
	   (command "erase" en1 "")
	   ;;)
	   (setq n (1+ n))
	 )
  )
  (print (strcat "处理" (rtos nn) "个实体"))
  nn
)
