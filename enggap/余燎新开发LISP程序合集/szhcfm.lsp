(defun c:szhcfm ( / c c_data old new)
  (setq oldosmode (getvar "osmode"))
  (setvar "osmode" 0)
  (setq oldorthomode (getvar "orthomode"))
  (setvar "orthomode" 0)
  (command "-text" "0,0" "0.5" "90" "00000")
  (setq c (entlast))
  (setq c_data (entget c))
  (setq old (assoc 41 c_data))
  (setq new (cons 41 1.5))
  (setq c_data (subst new old c_data))
  (entmod c_data)
  (command "chprop" "all" "" "c" "1" "")
  (command "move" (entlast) "" "0,0" "-21.6975,12.0199")
  (command "copy" (entlast) "" "m" "-21.9012,11.4483" "-20.8874,10.5922" "-1.1163,11.4483" "-0.1026,10.5922" "22.1922,11.4483" "23.2060,10.5922" "") 
        (command "pline" (list -21.4227 3.49238) "w" 0 0 
                         (list -21.6292 3.89621) 
                         (list -21.6292 3.18007) 
                         (list -21.578 3.18007) 
                         (list -21.578 3.68379) 
                         (list -21.4682 3.46909) 
                         "c"
         )
        (command "pline" (list 22.646 -15.6141) "w" 0 0 
                         (list 22.646 -14.4708) 
                         (list 23.3718 -14.4708) 
                         (list 23.3718 -15.6141) 
                         "c"
         )
        (command "pline" (list 21.5871 0.285422) "w" 0 0 
                         (list 21.5871 1.01123) 
                         (list 22.7304 1.01123) 
                         (list 22.7304 0.285422) 
                         "c"
         )
        (command "pline" (list -3.80359 -16.3154) "w" 0 0 
                         (list -3.80359 -13.7695) 
                         (list 2.73513 -13.7695) 
                         (list 2.73513 -16.3154) 
                         "c"
         )
        (command "pline" (list -1.80719 -3.47082) "w" 0 0 
                         (list -1.80719 3.0679) 
                         (list 0.738727 3.0679) 
                         (list 0.738727 -3.47082) 
                         "c"
         )
        (command "pline" (list -22.1563 -16.8171) "w" 0 0 
                         (list -22.1563 -13.2679) 
                         (list -19.1334 -13.2679) 
                         (list -19.1334 -16.8171) 
                         "c"
         )
        (command "pline" (list -23.2696 -0.863123) "w" 0 0 
                         (list -23.2696 2.15978) 
                         (list -19.7204 2.15978) 
                         (list -19.7204 -0.863123) 
                         "c"
         )
        (command "pline" (list 16.0894 18.4145) "w" 0 0 
                         (list 16.0894 -27.9206) 
                         (list 28.0492 -27.9206) 
                         (list 28.0492 19.7345) 
                         (list 16.2806 19.7345) 
                         (list 16.2806 19.6345) 
                         (list 27.9492 19.6345) 
                         (list 27.9492 -27.8206) 
                         (list 16.1894 -27.8206) 
                         (list 16.1894 18.4145) 
                         "c"
         )
        (command "pline" (list 18.0617 17.5678) "w" 0 0 
                         (list 18.0617 -25.7769) 
                         (list 18.1617 -25.7769) 
                         (list 18.1617 17.5678) 
                         "c"
         )
        (command "pline" (list 26.7487 17.5678) "w" 0 0 
                         (list 26.7487 -25.7769) 
                         (list 26.8487 -25.7769) 
                         (list 26.8487 17.5678) 
                         "c"
         )
        (command "pline" (list 20.1109 -23.3833) "w" 0 0 
                         (list 20.1109 -22.2528) 
                         (list 20.0109 -22.2528) 
                         (list 20.0109 -23.3833) 
                         "c"
         )
        (command "pline" (list 20.6064 -22.7783) "w" 0 0 
                         (list 19.5819 -22.7783) 
                         (list 19.5819 -22.8783) 
                         (list 20.6064 -22.8783) 
                         "c"
         )
        (command "pline" (list -1.17968 11.1315) "w" 0 0 
                         (list -1.17909 11.1254) 
                         (list -1.17798 11.1213) 
                         (list -1.17631 11.1173) 
                         (list -1.17413 11.1136) 
                         (list -1.17147 11.1103) 
                         (list -1.16837 11.1073) 
                         (list -1.1649 11.1047) 
                         (list -1.16112 11.1027) 
                         (list -1.15709 11.1012) 
                         (list -1.15291 11.1002) 
                         (list -1.14863 11.0999) 
                         (list -1.14433 11.1001) 
                         (list -1.14011 11.1009) 
                         (list -1.13603 11.1022) 
                         (list -1.13218 11.1041) 
                         (list -1.12861 11.1065) 
                         (list -1.1254 11.1094) 
                         (list -1.12261 11.1126) 
                         (list -1.12028 11.1162) 
                         (list -1.11847 11.1201) 
                         (list -1.11719 11.1242) 
                         (list -1.11649 11.1285) 
                         (list -1.11634 11.1315) 
                         (list -1.11635 11.7657) 
                         (list -1.11672 11.77) 
                         (list -1.11767 11.7742) 
                         (list -1.11918 11.7782) 
                         (list -1.12122 11.782) 
                         (list -1.12375 11.7855) 
                         (list -1.12673 11.7886) 
                         (list -1.1301 11.7912) 
                         (list -1.1338 11.7934) 
                         (list -1.13776 11.7951) 
                         (list -1.14191 11.7962) 
                         (list -1.14617 11.7967) 
                         (list -1.15047 11.7967) 
                         (list -1.15472 11.7961) 
                         (list -1.15884 11.7949) 
                         (list -1.16277 11.7931) 
                         (list -1.16643 11.7909) 
                         (list -1.16975 11.7882) 
                         (list -1.17266 11.785) 
                         (list -1.17513 11.7815) 
                         (list -1.17709 11.7777) 
                         (list -1.17852 11.7736) 
                         (list -1.17939 11.7694) 
                         (list -1.17968 11.7651) 
                         "c"
         )
        (command "pline" (list -0.83138 10.1493) "w" 0 0 
                         (list -0.825276 10.1499) 
                         (list -0.821127 10.151) 
                         (list -0.817166 10.1527) 
                         (list -0.813467 10.1549) 
                         (list -0.810097 10.1575) 
                         (list -0.807119 10.1606) 
                         (list -0.804587 10.1641) 
                         (list -0.802548 10.1679) 
                         (list -0.80104 10.1719) 
                         (list -0.800089 10.1761) 
                         (list -0.799715 10.1804) 
                         (list -0.799923 10.1847) 
                         (list -0.80071 10.1889) 
                         (list -0.802061 10.193) 
                         (list -0.803952 10.1968) 
                         (list -0.806347 10.2004) 
                         (list -0.809203 10.2036) 
                         (list -0.812467 10.2064) 
                         (list -0.816079 10.2087) 
                         (list -0.819973 10.2105) 
                         (list -0.824076 10.2118) 
                         (list -0.828314 10.2125) 
                         (list -0.83138 10.2127) 
                         (list -1.46494 10.2127) 
                         (list -1.46922 10.2123) 
                         (list -1.4734 10.2113) 
                         (list -1.47743 10.2098) 
                         (list -1.48121 10.2078) 
                         (list -1.48468 10.2053) 
                         (list -1.48778 10.2023) 
                         (list -1.49044 10.1989) 
                         (list -1.49262 10.1952) 
                         (list -1.49429 10.1913) 
                         (list -1.4954 10.1871) 
                         (list -1.49594 10.1828) 
                         (list -1.4959 10.1785) 
                         (list -1.49527 10.1743) 
                         (list -1.49408 10.1702) 
                         (list -1.49234 10.1662) 
                         (list -1.49009 10.1626) 
                         (list -1.48736 10.1593) 
                         (list -1.4842 10.1563) 
                         (list -1.48069 10.1539) 
                         (list -1.47687 10.1519) 
                         (list -1.47281 10.1505) 
                         (list -1.46861 10.1496) 
                         (list -1.46432 10.1493) 
                         "c"
         )
        (command "pline" (list -1.48334 10.2063) "w" 0 0 
                         (list -1.48787 10.2022) 
                         (list -1.49052 10.1988) 
                         (list -1.49268 10.1951) 
                         (list -1.49433 10.1911) 
                         (list -1.49542 10.187) 
                         (list -1.49595 10.1827) 
                         (list -1.49589 10.1784) 
                         (list -1.49525 10.1742) 
                         (list -1.49404 10.17) 
                         (list -1.49228 10.1661) 
                         (list -1.49001 10.1625) 
                         (list -1.48726 10.1592) 
                         (list -1.4841 10.1563) 
                         (list -1.48057 10.1538) 
                         (list -1.47674 10.1519) 
                         (list -1.47268 10.1505) 
                         (list -1.46847 10.1496) 
                         (list -1.46419 10.1493) 
                         (list -1.4599 10.1496) 
                         (list -1.4557 10.1505) 
                         (list -1.45165 10.152) 
                         (list -1.44784 10.154) 
                         (list -1.4453 10.1557) 
                         (list -1.02285 10.473) 
                         (list -1.01966 10.4759) 
                         (list -1.01688 10.4791) 
                         (list -1.01457 10.4828) 
                         (list -1.01277 10.4867) 
                         (list -1.01151 10.4908) 
                         (list -1.01083 10.495) 
                         (list -1.01072 10.4993) 
                         (list -1.01119 10.5036) 
                         (list -1.01224 10.5078) 
                         (list -1.01385 10.5117) 
                         (list -1.01597 10.5155) 
                         (list -1.01859 10.5189) 
                         (list -1.02164 10.5219) 
                         (list -1.02507 10.5245) 
                         (list -1.02882 10.5266) 
                         (list -1.03282 10.5282) 
                         (list -1.03699 10.5292) 
                         (list -1.04127 10.5296) 
                         (list -1.04556 10.5295) 
                         (list -1.0498 10.5287) 
                         (list -1.05389 10.5274) 
                         (list -1.05778 10.5256) 
                         (list -1.06138 10.5233) 
                         "c"
         )
        (command "pline" (list -1.06137 10.4726) "w" 0 0 
                         (list -1.05613 10.4694) 
                         (list -1.05214 10.4678) 
                         (list -1.04798 10.4668) 
                         (list -1.04371 10.4663) 
                         (list -1.03941 10.4664) 
                         (list -1.03517 10.4671) 
                         (list -1.03107 10.4684) 
                         (list -1.02717 10.4702) 
                         (list -1.02354 10.4725) 
                         (list -1.02027 10.4753) 
                         (list -1.0174 10.4785) 
                         (list -1.01499 10.482) 
                         (list -1.01309 10.4859) 
                         (list -1.01172 10.4899) 
                         (list -1.01092 10.4942) 
                         (list -1.01069 10.4984) 
                         (list -1.01105 10.5027) 
                         (list -1.01199 10.5069) 
                         (list -1.01348 10.5109) 
                         (list -1.0155 10.5147) 
                         (list -1.01802 10.5182) 
                         (list -1.02099 10.5213) 
                         (list -1.02335 10.5233) 
                         (list -1.44581 10.8403) 
                         (list -1.44946 10.8425) 
                         (list -1.45338 10.8443) 
                         (list -1.4575 10.8455) 
                         (list -1.46175 10.8462) 
                         (list -1.46604 10.8462) 
                         (list -1.47031 10.8457) 
                         (list -1.47446 10.8446) 
                         (list -1.47843 10.8429) 
                         (list -1.48214 10.8408) 
                         (list -1.48552 10.8381) 
                         (list -1.48851 10.835) 
                         (list -1.49105 10.8316) 
                         (list -1.4931 10.8278) 
                         (list -1.49463 10.8238) 
                         (list -1.49559 10.8196) 
                         (list -1.49598 10.8153) 
                         (list -1.49579 10.811) 
                         (list -1.49502 10.8068) 
                         (list -1.49368 10.8027) 
                         (list -1.49181 10.7989) 
                         (list -1.48943 10.7953) 
                         (list -1.48658 10.7921) 
                         (list -1.48333 10.7893) 
                         "c"
         )
        (command "pline" (list -1.46432 10.8463) "w" 0 0 
                         (list -1.47042 10.8457) 
                         (list -1.47457 10.8445) 
                         (list -1.47854 10.8429) 
                         (list -1.48223 10.8407) 
                         (list -1.4856 10.838) 
                         (list -1.48858 10.8349) 
                         (list -1.49111 10.8315) 
                         (list -1.49315 10.8277) 
                         (list -1.49466 10.8237) 
                         (list -1.49561 10.8195) 
                         (list -1.49599 10.8152) 
                         (list -1.49578 10.8109) 
                         (list -1.49499 10.8067) 
                         (list -1.49364 10.8026) 
                         (list -1.49175 10.7987) 
                         (list -1.48935 10.7952) 
                         (list -1.4865 10.792) 
                         (list -1.48323 10.7892) 
                         (list -1.47962 10.7869) 
                         (list -1.47573 10.785) 
                         (list -1.47163 10.7838) 
                         (list -1.46739 10.7831) 
                         (list -1.46432 10.7829) 
                         (list -0.830766 10.7829) 
                         (list -0.826486 10.7833) 
                         (list -0.822296 10.7842) 
                         (list -0.818274 10.7858) 
                         (list -0.814493 10.7878) 
                         (list -0.811022 10.7903) 
                         (list -0.807926 10.7933) 
                         (list -0.805262 10.7967) 
                         (list -0.803078 10.8004) 
                         (list -0.801415 10.8043) 
                         (list -0.800303 10.8085) 
                         (list -0.799763 10.8127) 
                         (list -0.799804 10.817) 
                         (list -0.800427 10.8213) 
                         (list -0.801619 10.8254) 
                         (list -0.803359 10.8293) 
                         (list -0.805614 10.833) 
                         (list -0.808343 10.8363) 
                         (list -0.811496 10.8392) 
                         (list -0.815015 10.8417) 
                         (list -0.818836 10.8437) 
                         (list -0.822886 10.8451) 
                         (list -0.827094 10.846) 
                         (list -0.83138 10.8463) 
                         "c"
         )
        (command "pline" (list -0.165931 10.2755) "w" 0 0 
                         (list -0.165337 10.2694) 
                         (list -0.164226 10.2652) 
                         (list -0.162562 10.2613) 
                         (list -0.160378 10.2576) 
                         (list -0.157714 10.2542) 
                         (list -0.154618 10.2512) 
                         (list -0.151147 10.2487) 
                         (list -0.147366 10.2466) 
                         (list -0.143344 10.2451) 
                         (list -0.139154 10.2442) 
                         (list -0.134875 10.2438) 
                         (list -0.130584 10.244) 
                         (list -0.126361 10.2448) 
                         (list -0.122283 10.2462) 
                         (list -0.118425 10.248) 
                         (list -0.114859 10.2504) 
                         (list -0.11165 10.2533) 
                         (list -0.108857 10.2566) 
                         (list -0.106531 10.2602) 
                         (list -0.104716 10.2641) 
                         (list -0.103444 10.2682) 
                         (list -0.102739 10.2724) 
                         (list -0.10259 10.2755) 
                         (list -0.102596 10.9096) 
                         (list -0.10297 10.9139) 
                         (list -0.103921 10.9181) 
                         (list -0.105429 10.9221) 
                         (list -0.107468 10.9259) 
                         (list -0.11 10.9293) 
                         (list -0.112978 10.9324) 
                         (list -0.116347 10.9351) 
                         (list -0.120047 10.9373) 
                         (list -0.124008 10.939) 
                         (list -0.128157 10.9401) 
                         (list -0.132419 10.9406) 
                         (list -0.136715 10.9406) 
                         (list -0.140965 10.9399) 
                         (list -0.145093 10.9387) 
                         (list -0.14902 10.937) 
                         (list -0.152677 10.9348) 
                         (list -0.155994 10.932) 
                         (list -0.158912 10.9289) 
                         (list -0.161376 10.9254) 
                         (list -0.163341 10.9215) 
                         (list -0.164771 10.9175) 
                         (list -0.16564 10.9133) 
                         (list -0.165931 10.909) 
                         "c"
         )
        (command "pline" (list 0.182068 9.29311) "w" 0 0 
                         (list 0.188172 9.29371) 
                         (list 0.192321 9.29482) 
                         (list 0.196282 9.29648) 
                         (list 0.199981 9.29867) 
                         (list 0.203351 9.30133) 
                         (list 0.206329 9.30443) 
                         (list 0.208861 9.3079) 
                         (list 0.2109 9.31168) 
                         (list 0.212408 9.3157) 
                         (list 0.213358 9.31989) 
                         (list 0.213733 9.32417) 
                         (list 0.213525 9.32846) 
                         (list 0.212738 9.33268) 
                         (list 0.211386 9.33676) 
                         (list 0.209496 9.34062) 
                         (list 0.2071 9.34419) 
                         (list 0.204245 9.3474) 
                         (list 0.200981 9.35019) 
                         (list 0.197369 9.35251) 
                         (list 0.193475 9.35433) 
                         (list 0.189372 9.3556) 
                         (list 0.185134 9.35631) 
                         (list 0.182068 9.35646) 
                         (list -0.45163 9.35645) 
                         (list -0.455909 9.35607) 
                         (list -0.460099 9.35512) 
                         (list -0.464121 9.35362) 
                         (list -0.467903 9.35158) 
                         (list -0.471373 9.34905) 
                         (list -0.474469 9.34607) 
                         (list -0.477134 9.3427) 
                         (list -0.479318 9.339) 
                         (list -0.480981 9.33504) 
                         (list -0.482093 9.33089) 
                         (list -0.482633 9.32663) 
                         (list -0.482591 9.32233) 
                         (list -0.481968 9.31808) 
                         (list -0.480776 9.31395) 
                         (list -0.479037 9.31002) 
                         (list -0.476781 9.30637) 
                         (list -0.474052 9.30305) 
                         (list -0.470899 9.30013) 
                         (list -0.46738 9.29767) 
                         (list -0.46356 9.2957) 
                         (list -0.459509 9.29427) 
                         (list -0.455302 9.29341) 
                         (list -0.451016 9.29311) 
                         "c"
         )
        (command "pline" (list -0.482686 9.32478) "w" 0 0 
                         (list -0.482093 9.31868) 
                         (list -0.480981 9.31453) 
                         (list -0.479318 9.31057) 
                         (list -0.477134 9.30687) 
                         (list -0.474469 9.3035) 
                         (list -0.471373 9.30052) 
                         (list -0.467903 9.29799) 
                         (list -0.464121 9.29595) 
                         (list -0.460099 9.29444) 
                         (list -0.455909 9.29349) 
                         (list -0.45163 9.29312) 
                         (list -0.447339 9.29333) 
                         (list -0.443116 9.29412) 
                         (list -0.439038 9.29547) 
                         (list -0.43518 9.29736) 
                         (list -0.431614 9.29975) 
                         (list -0.428405 9.30261) 
                         (list -0.425612 9.30587) 
                         (list -0.423286 9.30948) 
                         (list -0.421471 9.31338) 
                         (list -0.420199 9.31748) 
                         (list -0.419494 9.32172) 
                         (list -0.419345 9.32478) 
                         (list -0.419351 9.80074) 
                         (list -0.419726 9.80502) 
                         (list -0.420676 9.80921) 
                         (list -0.422184 9.81324) 
                         (list -0.424223 9.81702) 
                         (list -0.426755 9.82049) 
                         (list -0.429733 9.82358) 
                         (list -0.433103 9.82625) 
                         (list -0.436802 9.82843) 
                         (list -0.440763 9.8301) 
                         (list -0.444912 9.83121) 
                         (list -0.449174 9.83175) 
                         (list -0.45347 9.83171) 
                         (list -0.457721 9.83108) 
                         (list -0.461848 9.82989) 
                         (list -0.465776 9.82815) 
                         (list -0.469432 9.8259) 
                         (list -0.472749 9.82317) 
                         (list -0.475667 9.82001) 
                         (list -0.478131 9.81649) 
                         (list -0.480096 9.81267) 
                         (list -0.481526 9.80862) 
                         (list -0.482395 9.80442) 
                         (list -0.482686 9.80013) 
                         "c"
         )
        (command "pline" (list -0.477378 9.81768) "w" 0 0 
                         (list -0.480266 9.81227) 
                         (list -0.48164 9.8082) 
                         (list -0.482451 9.80398) 
                         (list -0.482683 9.79969) 
                         (list -0.482333 9.79541) 
                         (list -0.481406 9.79122) 
                         (list -0.47992 9.78719) 
                         (list -0.477903 9.78339) 
                         (list -0.475391 9.77991) 
                         (list -0.47243 9.7768) 
                         (list -0.469075 9.77411) 
                         (list -0.465388 9.77191) 
                         (list -0.461436 9.77022) 
                         (list -0.457293 9.76909) 
                         (list -0.453034 9.76852) 
                         (list -0.448739 9.76854) 
                         (list -0.444485 9.76914) 
                         (list -0.440351 9.77031) 
                         (list -0.436413 9.77203) 
                         (list -0.432744 9.77426) 
                         (list -0.429412 9.77697) 
                         (list -0.426476 9.78011) 
                         (list -0.424653 9.78258) 
                         (list -0.319017 9.94126) 
                         (list -0.316957 9.94503) 
                         (list -0.315426 9.94904) 
                         (list -0.314453 9.95323) 
                         (list -0.314054 9.9575) 
                         (list -0.314238 9.9618) 
                         (list -0.315002 9.96602) 
                         (list -0.31633 9.97011) 
                         (list -0.318199 9.97398) 
                         (list -0.320574 9.97756) 
                         (list -0.323412 9.98078) 
                         (list -0.326661 9.98359) 
                         (list -0.330259 9.98594) 
                         (list -0.334142 9.98778) 
                         (list -0.338239 9.98907) 
                         (list -0.342472 9.9898) 
                         (list -0.346766 9.98995) 
                         (list -0.35104 9.98951) 
                         (list -0.355216 9.98851) 
                         (list -0.359217 9.98694) 
                         (list -0.36297 9.98485) 
                         (list -0.366405 9.98227) 
                         (list -0.36946 9.97925) 
                         (list -0.372077 9.97585) 
                         "c"
         )
        (command "pline" (list -0.345715 9.98997) "w" 0 0 
                         (list -0.351818 9.98937) 
                         (list -0.355968 9.98826) 
                         (list -0.359929 9.9866) 
                         (list -0.363628 9.98441) 
                         (list -0.366998 9.98175) 
                         (list -0.369976 9.97865) 
                         (list -0.372508 9.97518) 
                         (list -0.374547 9.9714) 
                         (list -0.376055 9.96738) 
                         (list -0.377005 9.96319) 
                         (list -0.37738 9.95891) 
                         (list -0.377171 9.95462) 
                         (list -0.376384 9.9504) 
                         (list -0.375033 9.94632) 
                         (list -0.373142 9.94246) 
                         (list -0.370747 9.93889) 
                         (list -0.367891 9.93568) 
                         (list -0.364627 9.93289) 
                         (list -0.361015 9.93057) 
                         (list -0.357122 9.92875) 
                         (list -0.353019 9.92748) 
                         (list -0.348781 9.92677) 
                         (list -0.345715 9.92662) 
                         (list -0.239374 9.92663) 
                         (list -0.235094 9.927) 
                         (list -0.230905 9.92795) 
                         (list -0.226882 9.92946) 
                         (list -0.223101 9.9315) 
                         (list -0.21963 9.93403) 
                         (list -0.216534 9.93701) 
                         (list -0.21387 9.94038) 
                         (list -0.211686 9.94408) 
                         (list -0.210023 9.94804) 
                         (list -0.208911 9.95219) 
                         (list -0.208371 9.95645) 
                         (list -0.208412 9.96075) 
                         (list -0.209035 9.965) 
                         (list -0.210227 9.96913) 
                         (list -0.211967 9.97305) 
                         (list -0.214222 9.97671) 
                         (list -0.216951 9.98003) 
                         (list -0.220105 9.98295) 
                         (list -0.223624 9.98541) 
                         (list -0.227444 9.98738) 
                         (list -0.231495 9.98881) 
                         (list -0.235702 9.98967) 
                         (list -0.239988 9.98997) 
                         "c"
         )
        (command "pline" (list -0.213658 9.9759) "w" 0 0 
                         (list -0.217543 9.98064) 
                         (list -0.220774 9.98347) 
                         (list -0.224358 9.98584) 
                         (list -0.228229 9.9877) 
                         (list -0.232317 9.98902) 
                         (list -0.236546 9.98978) 
                         (list -0.240838 9.98995) 
                         (list -0.245115 9.98955) 
                         (list -0.249297 9.98857) 
                         (list -0.253308 9.98703) 
                         (list -0.257074 9.98496) 
                         (list -0.260526 9.9824) 
                         (list -0.263599 9.9794) 
                         (list -0.266239 9.97601) 
                         (list -0.268395 9.9723) 
                         (list -0.270029 9.96832) 
                         (list -0.271109 9.96417) 
                         (list -0.271618 9.9599) 
                         (list -0.271544 9.9556) 
                         (list -0.27089 9.95136) 
                         (list -0.269667 9.94724) 
                         (list -0.267898 9.94333) 
                         (list -0.266317 9.94069) 
                         (list -0.160244 9.78202) 
                         (list -0.157554 9.77867) 
                         (list -0.154436 9.77572) 
                         (list -0.150947 9.77321) 
                         (list -0.14715 9.7712) 
                         (list -0.143117 9.76972) 
                         (list -0.13892 9.7688) 
                         (list -0.134638 9.76846) 
                         (list -0.130349 9.7687) 
                         (list -0.126132 9.76952) 
                         (list -0.122064 9.7709) 
                         (list -0.118221 9.77282) 
                         (list -0.114673 9.77524) 
                         (list -0.111485 9.77812) 
                         (list -0.108716 9.78141) 
                         (list -0.106418 9.78504) 
                         (list -0.104631 9.78894) 
                         (list -0.10339 9.79306) 
                         (list -0.102717 9.7973) 
                         (list -0.102624 9.80159) 
                         (list -0.103113 9.80586) 
                         (list -0.104175 9.81003) 
                         (list -0.105791 9.81401) 
                         (list -0.107931 9.81773) 
                         "c"
         )
        (command "pline" (list -0.10259 9.80013) "w" 0 0 
                         (list -0.103184 9.80623) 
                         (list -0.104296 9.81038) 
                         (list -0.105959 9.81434) 
                         (list -0.108143 9.81804) 
                         (list -0.110807 9.82141) 
                         (list -0.113903 9.82439) 
                         (list -0.117374 9.82692) 
                         (list -0.121155 9.82896) 
                         (list -0.125177 9.83047) 
                         (list -0.129367 9.83142) 
                         (list -0.133646 9.8318) 
                         (list -0.137937 9.83159) 
                         (list -0.142161 9.8308) 
                         (list -0.146238 9.82945) 
                         (list -0.150096 9.82756) 
                         (list -0.153662 9.82516) 
                         (list -0.156871 9.82231) 
                         (list -0.159664 9.81904) 
                         (list -0.16199 9.81543) 
                         (list -0.163806 9.81154) 
                         (list -0.165077 9.80743) 
                         (list -0.165782 9.8032) 
                         (list -0.165931 9.80013) 
                         (list -0.165925 9.32417) 
                         (list -0.165551 9.31989) 
                         (list -0.164601 9.3157) 
                         (list -0.163092 9.31168) 
                         (list -0.161053 9.3079) 
                         (list -0.158522 9.30443) 
                         (list -0.155543 9.30133) 
                         (list -0.152174 9.29867) 
                         (list -0.148474 9.29648) 
                         (list -0.144513 9.29482) 
                         (list -0.140364 9.29371) 
                         (list -0.136102 9.29317) 
                         (list -0.131806 9.29321) 
                         (list -0.127556 9.29383) 
                         (list -0.123429 9.29502) 
                         (list -0.119501 9.29676) 
                         (list -0.115844 9.29902) 
                         (list -0.112527 9.30175) 
                         (list -0.109609 9.3049) 
                         (list -0.107145 9.30842) 
                         (list -0.10518 9.31224) 
                         (list -0.10375 9.31629) 
                         (list -0.102881 9.3205) 
                         (list -0.10259 9.32478) 
                         "c"
         )
        (command "pline" (list -2.22946 -22.7783) "w" 0 0 
                         (list -3.25396 -22.7783) 
                         (list -3.25396 -22.8783) 
                         (list -2.22946 -22.8783) 
                         "c"
         )
        (command "pline" (list -2.72496 -23.3833) "w" 0 0 
                         (list -2.72496 -22.2528) 
                         (list -2.82496 -22.2528) 
                         (list -2.82496 -23.3833) 
                         "c"
         )
        (command "pline" (list -9.29077 17.5678) "w" 0 0 
                         (list -9.29077 -25.7769) 
                         (list -9.19077 -25.7769) 
                         (list -9.19077 17.5678) 
                         "c"
         )
        (command "pline" (list 8.1223 17.5678) "w" 0 0 
                         (list 8.1223 -25.7769) 
                         (list 8.2223 -25.7769) 
                         (list 8.2223 17.5678) 
                         "c"
         )
        (command "pline" (list -23.0474 -22.7783) "w" 0 0 
                         (list -24.0719 -22.7783) 
                         (list -24.0719 -22.8783) 
                         (list -23.0474 -22.8783) 
                         "c"
         )
        (command "pline" (list -23.5429 -23.3833) "w" 0 0 
                         (list -23.5429 -22.2528) 
                         (list -23.6429 -22.2528) 
                         (list -23.6429 -23.3833) 
                         "c"
         )
        (command "pline" (list -16.9051 17.5678) "w" 0 0 
                         (list -16.9051 -25.7769) 
                         (list -16.8051 -25.7769) 
                         (list -16.8051 17.5678) 
                         "c"
         )
        (command "pline" (list -25.2921 17.5678) "w" 0 0 
                         (list -25.2921 -25.7769) 
                         (list -25.1921 -25.7769) 
                         (list -25.1921 17.5678) 
                         "c"
         )
        (command "pline" (list -27.5644 18.4145) "w" 0 0 
                         (list -27.5644 -27.9206) 
                         (list -15.6046 -27.9206) 
                         (list -15.6046 19.7345) 
                         (list -27.3732 19.7345) 
                         (list -27.3732 19.6345) 
                         (list -15.7046 19.6345) 
                         (list -15.7046 -27.8206) 
                         (list -27.4644 -27.8206) 
                         (list -27.4644 18.4145) 
                         "c"
         )
        (command "pline" (list 10.6441 19.7345) "w" 0 0 
                         (list 10.5441 19.7345) 
                         (list 10.5441 -27.9206) 
                         (list 10.6441 -27.9206) 
                         "c"
         )
        (command "pline" (list -10.5787 19.7345) "w" 0 0 
                         (list -10.5787 19.6345) 
                         (list 10.5941 19.6345) 
                         (list 10.5941 19.7345) 
                         "c"
         )
        (command "pline" (list -11.8378 -27.8706) "w" 0 0 
                         (list -11.7378 -27.8706) 
                         (list -11.7378 18.4145) 
                         (list -11.8378 18.4145) 
                         "c"
         )
        (command "pline" (list 10.5941 -27.9206) "w" 0 0 
                         (list 10.5941 -27.8206) 
                         (list -11.8378 -27.8206) 
                         (list -11.8378 -27.9206) 
                         "c"
         )
        (command "pline" (list -38.05 -38.05) "w" 0 0 
                         (list -38.05 -37.65) 
                         (list -38.15 -37.65) 
                         (list -38.15 -38.15) 
                         (list -18.6 -38.15) 
                         (list -18.6 -38.05) 
                         (list -18.2 -38.05) 
                         (list -18.2 -38.25) 
                         (list -18.0 -38.25) 
                         (list -18.0 -38.05) 
                         (list -17.6 -38.05) 
                         (list -17.6 -38.15) 
                         (list 17.6 -38.15) 
                         (list 17.6 -38.05) 
                         (list 18.0 -38.05) 
                         (list 18.0 -38.25) 
                         (list 18.2 -38.25) 
                         (list 18.2 -38.05) 
                         (list 18.6 -38.05) 
                         (list 18.6 -38.15) 
                         (list 38.15 -38.15) 
                         (list 38.15 -18.6) 
                         (list 38.05 -18.6) 
                         (list 38.05 -18.2) 
                         (list 38.25 -18.2) 
                         (list 38.25 -18.0) 
                         (list 38.05 -18.0) 
                         (list 38.05 -17.6) 
                         (list 38.15 -17.6) 
                         (list 38.15 17.6) 
                         (list 38.05 17.6) 
                         (list 38.05 18.0) 
                         (list 38.25 18.0) 
                         (list 38.25 18.2) 
                         (list 38.05 18.2) 
                         (list 38.05 18.6) 
                         (list 38.15 18.6) 
                         (list 38.15 38.15) 
                         (list 18.6 38.15) 
                         (list 18.6 38.05) 
                         (list 18.2 38.05) 
                         (list 18.2 38.25) 
                         (list 18.0 38.25) 
                         (list 18.0 38.05) 
                         (list 17.6 38.05) 
                         (list 17.6 38.15) 
                         (list -17.6 38.15) 
                         (list -17.6 38.05) 
                         (list -18.0 38.05) 
                         (list -18.0 38.25) 
                         (list -18.2 38.25) 
                         (list -18.2 38.05) 
                         (list -18.6 38.05) 
                         (list -18.6 38.15) 
                         (list -38.15 38.15) 
                         (list -38.15 18.6) 
                         (list -38.05 18.6) 
                         (list -38.05 18.2) 
                         (list -38.25 18.2) 
                         (list -38.25 18.0) 
                         (list -38.05 18.0) 
                         (list -38.05 17.6) 
                         (list -38.15 17.6) 
                         (list -38.15 -17.6) 
                         (list -38.05 -17.6) 
                         (list -38.05 -18.0) 
                         (list -38.25 -18.0) 
                         (list -38.25 -18.2) 
                         (list -38.05 -18.2) 
                         (list -38.05 -18.6) 
                         (list -38.15 -18.6) 
                         (list -38.15 -37.15) 
                         (list -38.05 -37.15) 
                         (list -38.05 -18.2) 
                         (list -37.95 -18.2) 
                         (list -37.95 -18.0) 
                         (list -38.05 -18.0) 
                         (list -38.05 18.0) 
                         (list -37.95 18.0) 
                         (list -37.95 18.2) 
                         (list -38.05 18.2) 
                         (list -38.05 38.05) 
                         (list -18.2 38.05) 
                         (list -18.2 37.95) 
                         (list -18.0 37.95) 
                         (list -18.0 38.05) 
                         (list 18.0 38.05) 
                         (list 18.0 37.95) 
                         (list 18.2 37.95) 
                         (list 18.2 38.05) 
                         (list 38.05 38.05) 
                         (list 38.05 18.2) 
                         (list 37.95 18.2) 
                         (list 37.95 18.0) 
                         (list 38.05 18.0) 
                         (list 38.05 -18.0) 
                         (list 37.95 -18.0) 
                         (list 37.95 -18.2) 
                         (list 38.05 -18.2) 
                         (list 38.05 -38.05) 
                         (list 18.2 -38.05) 
                         (list 18.2 -37.95) 
                         (list 18.0 -37.95) 
                         (list 18.0 -38.05) 
                         (list -18.0 -38.05) 
                         (list -18.0 -37.95) 
                         (list -18.2 -37.95) 
                         (list -18.2 -38.05) 
                         "c"
         )
        (command "pline" (list 23.206 9.80013) "w" 0 0 
                         (list 23.2054 9.80623) 
                         (list 23.2043 9.81038) 
                         (list 23.2026 9.81434) 
                         (list 23.2004 9.81804) 
                         (list 23.1978 9.82141) 
                         (list 23.1947 9.82439) 
                         (list 23.1912 9.82692) 
                         (list 23.1874 9.82896) 
                         (list 23.1834 9.83047) 
                         (list 23.1792 9.83142) 
                         (list 23.1749 9.8318) 
                         (list 23.1706 9.83159) 
                         (list 23.1664 9.8308) 
                         (list 23.1623 9.82945) 
                         (list 23.1585 9.82756) 
                         (list 23.1549 9.82516) 
                         (list 23.1517 9.82231) 
                         (list 23.1489 9.81904) 
                         (list 23.1466 9.81543) 
                         (list 23.1448 9.81154) 
                         (list 23.1435 9.80743) 
                         (list 23.1428 9.8032) 
                         (list 23.1426 9.80013) 
                         (list 23.1426 9.32417) 
                         (list 23.143 9.31989) 
                         (list 23.144 9.3157) 
                         (list 23.1455 9.31168) 
                         (list 23.1475 9.3079) 
                         (list 23.15 9.30443) 
                         (list 23.153 9.30133) 
                         (list 23.1564 9.29867) 
                         (list 23.1601 9.29648) 
                         (list 23.164 9.29482) 
                         (list 23.1682 9.29371) 
                         (list 23.1725 9.29317) 
                         (list 23.1768 9.29321) 
                         (list 23.181 9.29383) 
                         (list 23.1851 9.29502) 
                         (list 23.1891 9.29676) 
                         (list 23.1927 9.29902) 
                         (list 23.196 9.30175) 
                         (list 23.199 9.3049) 
                         (list 23.2014 9.30842) 
                         (list 23.2034 9.31224) 
                         (list 23.2048 9.31629) 
                         (list 23.2057 9.3205) 
                         (list 23.206 9.32478) 
                         "c"
         )
        (command "pline" (list 23.0949 9.9759) "w" 0 0 
                         (list 23.091 9.98064) 
                         (list 23.0878 9.98347) 
                         (list 23.0842 9.98584) 
                         (list 23.0803 9.9877) 
                         (list 23.0762 9.98902) 
                         (list 23.072 9.98978) 
                         (list 23.0677 9.98995) 
                         (list 23.0634 9.98955) 
                         (list 23.0593 9.98857) 
                         (list 23.0553 9.98703) 
                         (list 23.0515 9.98496) 
                         (list 23.048 9.9824) 
                         (list 23.045 9.9794) 
                         (list 23.0423 9.97601) 
                         (list 23.0402 9.9723) 
                         (list 23.0385 9.96832) 
                         (list 23.0375 9.96417) 
                         (list 23.0369 9.9599) 
                         (list 23.037 9.9556) 
                         (list 23.0377 9.95136) 
                         (list 23.0389 9.94724) 
                         (list 23.0407 9.94333) 
                         (list 23.0422 9.94069) 
                         (list 23.1483 9.78202) 
                         (list 23.151 9.77867) 
                         (list 23.1541 9.77572) 
                         (list 23.1576 9.77321) 
                         (list 23.1614 9.7712) 
                         (list 23.1654 9.76972) 
                         (list 23.1696 9.7688) 
                         (list 23.1739 9.76846) 
                         (list 23.1782 9.7687) 
                         (list 23.1824 9.76952) 
                         (list 23.1865 9.7709) 
                         (list 23.1903 9.77282) 
                         (list 23.1939 9.77524) 
                         (list 23.1971 9.77812) 
                         (list 23.1998 9.78141) 
                         (list 23.2021 9.78504) 
                         (list 23.2039 9.78894) 
                         (list 23.2052 9.79306) 
                         (list 23.2058 9.7973) 
                         (list 23.2059 9.80159) 
                         (list 23.2054 9.80586) 
                         (list 23.2044 9.81003) 
                         (list 23.2028 9.81401) 
                         (list 23.2006 9.81773) 
                         "c"
         )
        (command "pline" (list 22.9628 9.98997) "w" 0 0 
                         (list 22.9567 9.98937) 
                         (list 22.9526 9.98826) 
                         (list 22.9486 9.9866) 
                         (list 22.9449 9.98441) 
                         (list 22.9416 9.98175) 
                         (list 22.9386 9.97865) 
                         (list 22.9361 9.97518) 
                         (list 22.934 9.9714) 
                         (list 22.9325 9.96738) 
                         (list 22.9316 9.96319) 
                         (list 22.9312 9.95891) 
                         (list 22.9314 9.95462) 
                         (list 22.9322 9.9504) 
                         (list 22.9335 9.94632) 
                         (list 22.9354 9.94246) 
                         (list 22.9378 9.93889) 
                         (list 22.9407 9.93568) 
                         (list 22.9439 9.93289) 
                         (list 22.9475 9.93057) 
                         (list 22.9514 9.92875) 
                         (list 22.9555 9.92748) 
                         (list 22.9598 9.92677) 
                         (list 22.9628 9.92662) 
                         (list 23.0692 9.92663) 
                         (list 23.0735 9.927) 
                         (list 23.0777 9.92795) 
                         (list 23.0817 9.92946) 
                         (list 23.0855 9.9315) 
                         (list 23.0889 9.93403) 
                         (list 23.092 9.93701) 
                         (list 23.0947 9.94038) 
                         (list 23.0969 9.94408) 
                         (list 23.0985 9.94804) 
                         (list 23.0996 9.95219) 
                         (list 23.1002 9.95645) 
                         (list 23.1001 9.96075) 
                         (list 23.0995 9.965) 
                         (list 23.0983 9.96913) 
                         (list 23.0966 9.97305) 
                         (list 23.0943 9.97671) 
                         (list 23.0916 9.98003) 
                         (list 23.0885 9.98295) 
                         (list 23.0849 9.98541) 
                         (list 23.0811 9.98738) 
                         (list 23.0771 9.98881) 
                         (list 23.0729 9.98967) 
                         (list 23.0686 9.98997) 
                         "c"
         )
        (command "pline" (list 22.8312 9.81768) "w" 0 0 
                         (list 22.8283 9.81227) 
                         (list 22.8269 9.8082) 
                         (list 22.8261 9.80398) 
                         (list 22.8259 9.79969) 
                         (list 22.8262 9.79541) 
                         (list 22.8272 9.79122) 
                         (list 22.8286 9.78719) 
                         (list 22.8307 9.78339) 
                         (list 22.8332 9.77991) 
                         (list 22.8361 9.7768) 
                         (list 22.8395 9.77411) 
                         (list 22.8432 9.77191) 
                         (list 22.8471 9.77022) 
                         (list 22.8513 9.76909) 
                         (list 22.8555 9.76852) 
                         (list 22.8598 9.76854) 
                         (list 22.8641 9.76914) 
                         (list 22.8682 9.77031) 
                         (list 22.8721 9.77203) 
                         (list 22.8758 9.77426) 
                         (list 22.8791 9.77697) 
                         (list 22.8821 9.78011) 
                         (list 22.8839 9.78258) 
                         (list 22.9895 9.94126) 
                         (list 22.9916 9.94503) 
                         (list 22.9931 9.94904) 
                         (list 22.9941 9.95323) 
                         (list 22.9945 9.9575) 
                         (list 22.9943 9.9618) 
                         (list 22.9936 9.96602) 
                         (list 22.9922 9.97011) 
                         (list 22.9904 9.97398) 
                         (list 22.988 9.97756) 
                         (list 22.9851 9.98078) 
                         (list 22.9819 9.98359) 
                         (list 22.9783 9.98594) 
                         (list 22.9744 9.98778) 
                         (list 22.9703 9.98907) 
                         (list 22.9661 9.9898) 
                         (list 22.9618 9.98995) 
                         (list 22.9575 9.98951) 
                         (list 22.9533 9.98851) 
                         (list 22.9493 9.98694) 
                         (list 22.9456 9.98485) 
                         (list 22.9422 9.98227) 
                         (list 22.9391 9.97925) 
                         (list 22.9365 9.97585) 
                         "c"
         )
        (command "pline" (list 22.8259 9.32478) "w" 0 0 
                         (list 22.8265 9.31868) 
                         (list 22.8276 9.31453) 
                         (list 22.8292 9.31057) 
                         (list 22.8314 9.30687) 
                         (list 22.8341 9.3035) 
                         (list 22.8372 9.30052) 
                         (list 22.8407 9.29799) 
                         (list 22.8444 9.29595) 
                         (list 22.8485 9.29444) 
                         (list 22.8527 9.29349) 
                         (list 22.8569 9.29312) 
                         (list 22.8612 9.29333) 
                         (list 22.8654 9.29412) 
                         (list 22.8695 9.29547) 
                         (list 22.8734 9.29736) 
                         (list 22.8769 9.29975) 
                         (list 22.8802 9.30261) 
                         (list 22.8829 9.30587) 
                         (list 22.8853 9.30948) 
                         (list 22.8871 9.31338) 
                         (list 22.8884 9.31748) 
                         (list 22.8891 9.32172) 
                         (list 22.8892 9.32478) 
                         (list 22.8892 9.80074) 
                         (list 22.8888 9.80502) 
                         (list 22.8879 9.80921) 
                         (list 22.8864 9.81324) 
                         (list 22.8843 9.81702) 
                         (list 22.8818 9.82049) 
                         (list 22.8788 9.82358) 
                         (list 22.8755 9.82625) 
                         (list 22.8718 9.82843) 
                         (list 22.8678 9.8301) 
                         (list 22.8636 9.83121) 
                         (list 22.8594 9.83175) 
                         (list 22.8551 9.83171) 
                         (list 22.8508 9.83108) 
                         (list 22.8467 9.82989) 
                         (list 22.8428 9.82815) 
                         (list 22.8391 9.8259) 
                         (list 22.8358 9.82317) 
                         (list 22.8329 9.82001) 
                         (list 22.8304 9.81649) 
                         (list 22.8285 9.81267) 
                         (list 22.827 9.80862) 
                         (list 22.8262 9.80442) 
                         (list 22.8259 9.80013) 
                         "c"
         )
        (command "pline" (list 23.4906 9.29311) "w" 0 0 
                         (list 23.4967 9.29371) 
                         (list 23.5009 9.29482) 
                         (list 23.5048 9.29648) 
                         (list 23.5085 9.29867) 
                         (list 23.5119 9.30133) 
                         (list 23.5149 9.30443) 
                         (list 23.5174 9.3079) 
                         (list 23.5195 9.31168) 
                         (list 23.521 9.3157) 
                         (list 23.5219 9.31989) 
                         (list 23.5223 9.32417) 
                         (list 23.5221 9.32846) 
                         (list 23.5213 9.33268) 
                         (list 23.5199 9.33676) 
                         (list 23.5181 9.34062) 
                         (list 23.5157 9.34419) 
                         (list 23.5128 9.3474) 
                         (list 23.5095 9.35019) 
                         (list 23.5059 9.35251) 
                         (list 23.502 9.35433) 
                         (list 23.4979 9.3556) 
                         (list 23.4937 9.35631) 
                         (list 23.4906 9.35646) 
                         (list 22.8569 9.35645) 
                         (list 22.8527 9.35607) 
                         (list 22.8485 9.35512) 
                         (list 22.8444 9.35362) 
                         (list 22.8407 9.35158) 
                         (list 22.8372 9.34905) 
                         (list 22.8341 9.34607) 
                         (list 22.8314 9.3427) 
                         (list 22.8292 9.339) 
                         (list 22.8276 9.33504) 
                         (list 22.8265 9.33089) 
                         (list 22.8259 9.32663) 
                         (list 22.826 9.32233) 
                         (list 22.8266 9.31808) 
                         (list 22.8278 9.31395) 
                         (list 22.8295 9.31002) 
                         (list 22.8318 9.30637) 
                         (list 22.8345 9.30305) 
                         (list 22.8377 9.30013) 
                         (list 22.8412 9.29767) 
                         (list 22.845 9.2957) 
                         (list 22.8491 9.29427) 
                         (list 22.8533 9.29341) 
                         (list 22.8575 9.29311) 
                         "c"
         )
        (command "pline" (list 23.1426 10.2755) "w" 0 0 
                         (list 23.1432 10.2694) 
                         (list 23.1443 10.2652) 
                         (list 23.146 10.2613) 
                         (list 23.1482 10.2576) 
                         (list 23.1508 10.2542) 
                         (list 23.1539 10.2512) 
                         (list 23.1574 10.2487) 
                         (list 23.1612 10.2466) 
                         (list 23.1652 10.2451) 
                         (list 23.1694 10.2442) 
                         (list 23.1737 10.2438) 
                         (list 23.178 10.244) 
                         (list 23.1822 10.2448) 
                         (list 23.1863 10.2462) 
                         (list 23.1901 10.248) 
                         (list 23.1937 10.2504) 
                         (list 23.1969 10.2533) 
                         (list 23.1997 10.2566) 
                         (list 23.202 10.2602) 
                         (list 23.2038 10.2641) 
                         (list 23.2051 10.2682) 
                         (list 23.2058 10.2724) 
                         (list 23.206 10.2755) 
                         (list 23.206 10.9096) 
                         (list 23.2056 10.9139) 
                         (list 23.2046 10.9181) 
                         (list 23.2031 10.9221) 
                         (list 23.2011 10.9259) 
                         (list 23.1986 10.9293) 
                         (list 23.1956 10.9324) 
                         (list 23.1922 10.9351) 
                         (list 23.1885 10.9373) 
                         (list 23.1846 10.939) 
                         (list 23.1804 10.9401) 
                         (list 23.1761 10.9406) 
                         (list 23.1718 10.9406) 
                         (list 23.1676 10.9399) 
                         (list 23.1635 10.9387) 
                         (list 23.1595 10.937) 
                         (list 23.1559 10.9348) 
                         (list 23.1526 10.932) 
                         (list 23.1496 10.9289) 
                         (list 23.1472 10.9254) 
                         (list 23.1452 10.9215) 
                         (list 23.1438 10.9175) 
                         (list 23.1429 10.9133) 
                         (list 23.1426 10.909) 
                         "c"
         )
        (command "pline" (list 21.8442 10.8463) "w" 0 0 
                         (list 21.8381 10.8457) 
                         (list 21.834 10.8445) 
                         (list 21.83 10.8429) 
                         (list 21.8263 10.8407) 
                         (list 21.823 10.838) 
                         (list 21.82 10.8349) 
                         (list 21.8174 10.8315) 
                         (list 21.8154 10.8277) 
                         (list 21.8139 10.8237) 
                         (list 21.8129 10.8195) 
                         (list 21.8126 10.8152) 
                         (list 21.8128 10.8109) 
                         (list 21.8136 10.8067) 
                         (list 21.8149 10.8026) 
                         (list 21.8168 10.7987) 
                         (list 21.8192 10.7952) 
                         (list 21.8221 10.792) 
                         (list 21.8253 10.7892) 
                         (list 21.8289 10.7869) 
                         (list 21.8328 10.785) 
                         (list 21.8369 10.7838) 
                         (list 21.8412 10.7831) 
                         (list 21.8442 10.7829) 
                         (list 22.4778 10.7829) 
                         (list 22.4821 10.7833) 
                         (list 22.4863 10.7842) 
                         (list 22.4903 10.7858) 
                         (list 22.4941 10.7878) 
                         (list 22.4975 10.7903) 
                         (list 22.5006 10.7933) 
                         (list 22.5033 10.7967) 
                         (list 22.5055 10.8004) 
                         (list 22.5071 10.8043) 
                         (list 22.5083 10.8085) 
                         (list 22.5088 10.8127) 
                         (list 22.5088 10.817) 
                         (list 22.5081 10.8213) 
                         (list 22.5069 10.8254) 
                         (list 22.5052 10.8293) 
                         (list 22.5029 10.833) 
                         (list 22.5002 10.8363) 
                         (list 22.4971 10.8392) 
                         (list 22.4935 10.8417) 
                         (list 22.4897 10.8437) 
                         (list 22.4857 10.8451) 
                         (list 22.4815 10.846) 
                         (list 22.4772 10.8463) 
                         "c"
         )
        (command "pline" (list 22.2472 10.4726) "w" 0 0 
                         (list 22.2524 10.4694) 
                         (list 22.2564 10.4678) 
                         (list 22.2606 10.4668) 
                         (list 22.2649 10.4663) 
                         (list 22.2691 10.4664) 
                         (list 22.2734 10.4671) 
                         (list 22.2775 10.4684) 
                         (list 22.2814 10.4702) 
                         (list 22.285 10.4725) 
                         (list 22.2883 10.4753) 
                         (list 22.2912 10.4785) 
                         (list 22.2936 10.482) 
                         (list 22.2955 10.4859) 
                         (list 22.2968 10.4899) 
                         (list 22.2976 10.4942) 
                         (list 22.2979 10.4984) 
                         (list 22.2975 10.5027) 
                         (list 22.2966 10.5069) 
                         (list 22.2951 10.5109) 
                         (list 22.2931 10.5147) 
                         (list 22.2905 10.5182) 
                         (list 22.2876 10.5213) 
                         (list 22.2852 10.5233) 
                         (list 21.8628 10.8403) 
                         (list 21.8591 10.8425) 
                         (list 21.8552 10.8443) 
                         (list 21.8511 10.8455) 
                         (list 21.8468 10.8462) 
                         (list 21.8425 10.8462) 
                         (list 21.8383 10.8457) 
                         (list 21.8341 10.8446) 
                         (list 21.8301 10.8429) 
                         (list 21.8264 10.8408) 
                         (list 21.823 10.8381) 
                         (list 21.8201 10.835) 
                         (list 21.8175 10.8316) 
                         (list 21.8155 10.8278) 
                         (list 21.8139 10.8238) 
                         (list 21.813 10.8196) 
                         (list 21.8126 10.8153) 
                         (list 21.8128 10.811) 
                         (list 21.8135 10.8068) 
                         (list 21.8149 10.8027) 
                         (list 21.8168 10.7989) 
                         (list 21.8191 10.7953) 
                         (list 21.822 10.7921) 
                         (list 21.8252 10.7893) 
                         "c"
         )
        (command "pline" (list 21.8252 10.2063) "w" 0 0 
                         (list 21.8207 10.2022) 
                         (list 21.818 10.1988) 
                         (list 21.8159 10.1951) 
                         (list 21.8142 10.1911) 
                         (list 21.8131 10.187) 
                         (list 21.8126 10.1827) 
                         (list 21.8127 10.1784) 
                         (list 21.8133 10.1742) 
                         (list 21.8145 10.17) 
                         (list 21.8163 10.1661) 
                         (list 21.8186 10.1625) 
                         (list 21.8213 10.1592) 
                         (list 21.8245 10.1563) 
                         (list 21.828 10.1538) 
                         (list 21.8318 10.1519) 
                         (list 21.8359 10.1505) 
                         (list 21.8401 10.1496) 
                         (list 21.8444 10.1493) 
                         (list 21.8487 10.1496) 
                         (list 21.8529 10.1505) 
                         (list 21.8569 10.152) 
                         (list 21.8607 10.154) 
                         (list 21.8633 10.1557) 
                         (list 22.2857 10.473) 
                         (list 22.2889 10.4759) 
                         (list 22.2917 10.4791) 
                         (list 22.294 10.4828) 
                         (list 22.2958 10.4867) 
                         (list 22.297 10.4908) 
                         (list 22.2977 10.495) 
                         (list 22.2978 10.4993) 
                         (list 22.2974 10.5036) 
                         (list 22.2963 10.5078) 
                         (list 22.2947 10.5117) 
                         (list 22.2926 10.5155) 
                         (list 22.29 10.5189) 
                         (list 22.2869 10.5219) 
                         (list 22.2835 10.5245) 
                         (list 22.2797 10.5266) 
                         (list 22.2757 10.5282) 
                         (list 22.2716 10.5292) 
                         (list 22.2673 10.5296) 
                         (list 22.263 10.5295) 
                         (list 22.2588 10.5287) 
                         (list 22.2547 10.5274) 
                         (list 22.2508 10.5256) 
                         (list 22.2472 10.5233) 
                         "c"
         )
        (command "pline" (list 22.4772 10.1493) "w" 0 0 
                         (list 22.4833 10.1499) 
                         (list 22.4874 10.151) 
                         (list 22.4914 10.1527) 
                         (list 22.4951 10.1549) 
                         (list 22.4985 10.1575) 
                         (list 22.5014 10.1606) 
                         (list 22.504 10.1641) 
                         (list 22.506 10.1679) 
                         (list 22.5075 10.1719) 
                         (list 22.5085 10.1761) 
                         (list 22.5088 10.1804) 
                         (list 22.5086 10.1847) 
                         (list 22.5078 10.1889) 
                         (list 22.5065 10.193) 
                         (list 22.5046 10.1968) 
                         (list 22.5022 10.2004) 
                         (list 22.4994 10.2036) 
                         (list 22.4961 10.2064) 
                         (list 22.4925 10.2087) 
                         (list 22.4886 10.2105) 
                         (list 22.4845 10.2118) 
                         (list 22.4802 10.2125) 
                         (list 22.4772 10.2127) 
                         (list 21.8436 10.2127) 
                         (list 21.8393 10.2123) 
                         (list 21.8352 10.2113) 
                         (list 21.8311 10.2098) 
                         (list 21.8274 10.2078) 
                         (list 21.8239 10.2053) 
                         (list 21.8208 10.2023) 
                         (list 21.8181 10.1989) 
                         (list 21.8159 10.1952) 
                         (list 21.8143 10.1913) 
                         (list 21.8132 10.1871) 
                         (list 21.8126 10.1828) 
                         (list 21.8127 10.1785) 
                         (list 21.8133 10.1743) 
                         (list 21.8145 10.1702) 
                         (list 21.8162 10.1662) 
                         (list 21.8185 10.1626) 
                         (list 21.8212 10.1593) 
                         (list 21.8244 10.1563) 
                         (list 21.8279 10.1539) 
                         (list 21.8317 10.1519) 
                         (list 21.8357 10.1505) 
                         (list 21.84 10.1496) 
                         (list 21.8442 10.1493) 
                         "c"
         )
        (command "pline" (list 22.1289 11.1315) "w" 0 0 
                         (list 22.1295 11.1254) 
                         (list 22.1306 11.1213) 
                         (list 22.1322 11.1173) 
                         (list 22.1344 11.1136) 
                         (list 22.1371 11.1103) 
                         (list 22.1402 11.1073) 
                         (list 22.1437 11.1047) 
                         (list 22.1474 11.1027) 
                         (list 22.1515 11.1012) 
                         (list 22.1557 11.1002) 
                         (list 22.1599 11.0999) 
                         (list 22.1642 11.1001) 
                         (list 22.1684 11.1009) 
                         (list 22.1725 11.1022) 
                         (list 22.1764 11.1041) 
                         (list 22.1799 11.1065) 
                         (list 22.1832 11.1094) 
                         (list 22.186 11.1126) 
                         (list 22.1883 11.1162) 
                         (list 22.1901 11.1201) 
                         (list 22.1914 11.1242) 
                         (list 22.1921 11.1285) 
                         (list 22.1922 11.1315) 
                         (list 22.1922 11.7657) 
                         (list 22.1918 11.77) 
                         (list 22.1909 11.7742) 
                         (list 22.1894 11.7782) 
                         (list 22.1873 11.782) 
                         (list 22.1848 11.7855) 
                         (list 22.1818 11.7886) 
                         (list 22.1785 11.7912) 
                         (list 22.1748 11.7934) 
                         (list 22.1708 11.7951) 
                         (list 22.1667 11.7962) 
                         (list 22.1624 11.7967) 
                         (list 22.1581 11.7967) 
                         (list 22.1538 11.7961) 
                         (list 22.1497 11.7949) 
                         (list 22.1458 11.7931) 
                         (list 22.1421 11.7909) 
                         (list 22.1388 11.7882) 
                         (list 22.1359 11.785) 
                         (list 22.1334 11.7815) 
                         (list 22.1315 11.7777) 
                         (list 22.13 11.7736) 
                         (list 22.1292 11.7694) 
                         (list 22.1289 11.7651) 
                         "c"
         )
        (command "pline" (list -20.8874 9.80013) "w" 0 0 
                         (list -20.888 9.80623) 
                         (list -20.8891 9.81038) 
                         (list -20.8908 9.81434) 
                         (list -20.893 9.81804) 
                         (list -20.8956 9.82141) 
                         (list -20.8987 9.82439) 
                         (list -20.9022 9.82692) 
                         (list -20.906 9.82896) 
                         (list -20.91 9.83047) 
                         (list -20.9142 9.83142) 
                         (list -20.9185 9.8318) 
                         (list -20.9228 9.83159) 
                         (list -20.927 9.8308) 
                         (list -20.9311 9.82945) 
                         (list -20.9349 9.82756) 
                         (list -20.9385 9.82516) 
                         (list -20.9417 9.82231) 
                         (list -20.9445 9.81904) 
                         (list -20.9468 9.81543) 
                         (list -20.9486 9.81154) 
                         (list -20.9499 9.80743) 
                         (list -20.9506 9.8032) 
                         (list -20.9508 9.80013) 
                         (list -20.9508 9.32417) 
                         (list -20.9504 9.31989) 
                         (list -20.9494 9.3157) 
                         (list -20.9479 9.31168) 
                         (list -20.9459 9.3079) 
                         (list -20.9434 9.30443) 
                         (list -20.9404 9.30133) 
                         (list -20.937 9.29867) 
                         (list -20.9333 9.29648) 
                         (list -20.9293 9.29482) 
                         (list -20.9252 9.29371) 
                         (list -20.9209 9.29317) 
                         (list -20.9166 9.29321) 
                         (list -20.9124 9.29383) 
                         (list -20.9083 9.29502) 
                         (list -20.9043 9.29676) 
                         (list -20.9007 9.29902) 
                         (list -20.8974 9.30175) 
                         (list -20.8944 9.3049) 
                         (list -20.892 9.30842) 
                         (list -20.89 9.31224) 
                         (list -20.8886 9.31629) 
                         (list -20.8877 9.3205) 
                         (list -20.8874 9.32478) 
                         "c"
         )
        (command "pline" (list -20.9985 9.9759) "w" 0 0 
                         (list -21.0024 9.98064) 
                         (list -21.0056 9.98347) 
                         (list -21.0092 9.98584) 
                         (list -21.0131 9.9877) 
                         (list -21.0172 9.98902) 
                         (list -21.0214 9.98978) 
                         (list -21.0257 9.98995) 
                         (list -21.0299 9.98955) 
                         (list -21.0341 9.98857) 
                         (list -21.0381 9.98703) 
                         (list -21.0419 9.98496) 
                         (list -21.0454 9.9824) 
                         (list -21.0484 9.9794) 
                         (list -21.0511 9.97601) 
                         (list -21.0532 9.9723) 
                         (list -21.0549 9.96832) 
                         (list -21.0559 9.96417) 
                         (list -21.0565 9.9599) 
                         (list -21.0564 9.9556) 
                         (list -21.0557 9.95136) 
                         (list -21.0545 9.94724) 
                         (list -21.0527 9.94333) 
                         (list -21.0512 9.94069) 
                         (list -20.9451 9.78202) 
                         (list -20.9424 9.77867) 
                         (list -20.9393 9.77572) 
                         (list -20.9358 9.77321) 
                         (list -20.932 9.7712) 
                         (list -20.928 9.76972) 
                         (list -20.9238 9.7688) 
                         (list -20.9195 9.76846) 
                         (list -20.9152 9.7687) 
                         (list -20.911 9.76952) 
                         (list -20.9069 9.7709) 
                         (list -20.9031 9.77282) 
                         (list -20.8995 9.77524) 
                         (list -20.8963 9.77812) 
                         (list -20.8936 9.78141) 
                         (list -20.8913 9.78504) 
                         (list -20.8895 9.78894) 
                         (list -20.8882 9.79306) 
                         (list -20.8876 9.7973) 
                         (list -20.8875 9.80159) 
                         (list -20.8879 9.80586) 
                         (list -20.889 9.81003) 
                         (list -20.8906 9.81401) 
                         (list -20.8928 9.81773) 
                         "c"
         )
        (command "pline" (list -21.1305 9.98997) "w" 0 0 
                         (list -21.1367 9.98937) 
                         (list -21.1408 9.98826) 
                         (list -21.1448 9.9866) 
                         (list -21.1485 9.98441) 
                         (list -21.1518 9.98175) 
                         (list -21.1548 9.97865) 
                         (list -21.1573 9.97518) 
                         (list -21.1594 9.9714) 
                         (list -21.1609 9.96738) 
                         (list -21.1618 9.96319) 
                         (list -21.1622 9.95891) 
                         (list -21.162 9.95462) 
                         (list -21.1612 9.9504) 
                         (list -21.1599 9.94632) 
                         (list -21.158 9.94246) 
                         (list -21.1556 9.93889) 
                         (list -21.1527 9.93568) 
                         (list -21.1495 9.93289) 
                         (list -21.1459 9.93057) 
                         (list -21.142 9.92875) 
                         (list -21.1379 9.92748) 
                         (list -21.1336 9.92677) 
                         (list -21.1305 9.92662) 
                         (list -21.0242 9.92663) 
                         (list -21.0199 9.927) 
                         (list -21.0157 9.92795) 
                         (list -21.0117 9.92946) 
                         (list -21.0079 9.9315) 
                         (list -21.0045 9.93403) 
                         (list -21.0014 9.93701) 
                         (list -20.9987 9.94038) 
                         (list -20.9965 9.94408) 
                         (list -20.9949 9.94804) 
                         (list -20.9937 9.95219) 
                         (list -20.9932 9.95645) 
                         (list -20.9932 9.96075) 
                         (list -20.9939 9.965) 
                         (list -20.9951 9.96913) 
                         (list -20.9968 9.97305) 
                         (list -20.9991 9.97671) 
                         (list -21.0018 9.98003) 
                         (list -21.0049 9.98295) 
                         (list -21.0085 9.98541) 
                         (list -21.0123 9.98738) 
                         (list -21.0163 9.98881) 
                         (list -21.0205 9.98967) 
                         (list -21.0248 9.98997) 
                         "c"
         )
        (command "pline" (list -21.2622 9.81768) "w" 0 0 
                         (list -21.2651 9.81227) 
                         (list -21.2665 9.8082) 
                         (list -21.2673 9.80398) 
                         (list -21.2675 9.79969) 
                         (list -21.2672 9.79541) 
                         (list -21.2662 9.79122) 
                         (list -21.2648 9.78719) 
                         (list -21.2627 9.78339) 
                         (list -21.2602 9.77991) 
                         (list -21.2573 9.7768) 
                         (list -21.2539 9.77411) 
                         (list -21.2502 9.77191) 
                         (list -21.2463 9.77022) 
                         (list -21.2421 9.76909) 
                         (list -21.2379 9.76852) 
                         (list -21.2336 9.76854) 
                         (list -21.2293 9.76914) 
                         (list -21.2252 9.77031) 
                         (list -21.2212 9.77203) 
                         (list -21.2176 9.77426) 
                         (list -21.2142 9.77697) 
                         (list -21.2113 9.78011) 
                         (list -21.2095 9.78258) 
                         (list -21.1039 9.94126) 
                         (list -21.1018 9.94503) 
                         (list -21.1003 9.94904) 
                         (list -21.0993 9.95323) 
                         (list -21.0989 9.9575) 
                         (list -21.0991 9.9618) 
                         (list -21.0998 9.96602) 
                         (list -21.1012 9.97011) 
                         (list -21.103 9.97398) 
                         (list -21.1054 9.97756) 
                         (list -21.1082 9.98078) 
                         (list -21.1115 9.98359) 
                         (list -21.1151 9.98594) 
                         (list -21.119 9.98778) 
                         (list -21.1231 9.98907) 
                         (list -21.1273 9.9898) 
                         (list -21.1316 9.98995) 
                         (list -21.1359 9.98951) 
                         (list -21.1401 9.98851) 
                         (list -21.1441 9.98694) 
                         (list -21.1478 9.98485) 
                         (list -21.1512 9.98227) 
                         (list -21.1543 9.97925) 
                         (list -21.1569 9.97585) 
                         "c"
         )
        (command "pline" (list -21.2675 9.32478) "w" 0 0 
                         (list -21.2669 9.31868) 
                         (list -21.2658 9.31453) 
                         (list -21.2642 9.31057) 
                         (list -21.262 9.30687) 
                         (list -21.2593 9.3035) 
                         (list -21.2562 9.30052) 
                         (list -21.2527 9.29799) 
                         (list -21.249 9.29595) 
                         (list -21.2449 9.29444) 
                         (list -21.2407 9.29349) 
                         (list -21.2365 9.29312) 
                         (list -21.2322 9.29333) 
                         (list -21.228 9.29412) 
                         (list -21.2239 9.29547) 
                         (list -21.22 9.29736) 
                         (list -21.2164 9.29975) 
                         (list -21.2132 9.30261) 
                         (list -21.2104 9.30587) 
                         (list -21.2081 9.30948) 
                         (list -21.2063 9.31338) 
                         (list -21.205 9.31748) 
                         (list -21.2043 9.32172) 
                         (list -21.2042 9.32478) 
                         (list -21.2042 9.80074) 
                         (list -21.2046 9.80502) 
                         (list -21.2055 9.80921) 
                         (list -21.207 9.81324) 
                         (list -21.2091 9.81702) 
                         (list -21.2116 9.82049) 
                         (list -21.2146 9.82358) 
                         (list -21.2179 9.82625) 
                         (list -21.2216 9.82843) 
                         (list -21.2256 9.8301) 
                         (list -21.2297 9.83121) 
                         (list -21.234 9.83175) 
                         (list -21.2383 9.83171) 
                         (list -21.2426 9.83108) 
                         (list -21.2467 9.82989) 
                         (list -21.2506 9.82815) 
                         (list -21.2543 9.8259) 
                         (list -21.2576 9.82317) 
                         (list -21.2605 9.82001) 
                         (list -21.263 9.81649) 
                         (list -21.2649 9.81267) 
                         (list -21.2664 9.80862) 
                         (list -21.2672 9.80442) 
                         (list -21.2675 9.80013) 
                         "c"
         )
        (command "pline" (list -20.6028 9.29311) "w" 0 0 
                         (list -20.5967 9.29371) 
                         (list -20.5925 9.29482) 
                         (list -20.5886 9.29648) 
                         (list -20.5849 9.29867) 
                         (list -20.5815 9.30133) 
                         (list -20.5785 9.30443) 
                         (list -20.576 9.3079) 
                         (list -20.5739 9.31168) 
                         (list -20.5724 9.3157) 
                         (list -20.5715 9.31989) 
                         (list -20.5711 9.32417) 
                         (list -20.5713 9.32846) 
                         (list -20.5721 9.33268) 
                         (list -20.5734 9.33676) 
                         (list -20.5753 9.34062) 
                         (list -20.5777 9.34419) 
                         (list -20.5806 9.3474) 
                         (list -20.5839 9.35019) 
                         (list -20.5875 9.35251) 
                         (list -20.5914 9.35433) 
                         (list -20.5955 9.3556) 
                         (list -20.5997 9.35631) 
                         (list -20.6028 9.35646) 
                         (list -21.2365 9.35645) 
                         (list -21.2407 9.35607) 
                         (list -21.2449 9.35512) 
                         (list -21.249 9.35362) 
                         (list -21.2527 9.35158) 
                         (list -21.2562 9.34905) 
                         (list -21.2593 9.34607) 
                         (list -21.262 9.3427) 
                         (list -21.2642 9.339) 
                         (list -21.2658 9.33504) 
                         (list -21.2669 9.33089) 
                         (list -21.2675 9.32663) 
                         (list -21.2674 9.32233) 
                         (list -21.2668 9.31808) 
                         (list -21.2656 9.31395) 
                         (list -21.2639 9.31002) 
                         (list -21.2616 9.30637) 
                         (list -21.2589 9.30305) 
                         (list -21.2557 9.30013) 
                         (list -21.2522 9.29767) 
                         (list -21.2484 9.2957) 
                         (list -21.2443 9.29427) 
                         (list -21.2401 9.29341) 
                         (list -21.2359 9.29311) 
                         "c"
         )
        (command "pline" (list -20.9508 10.2755) "w" 0 0 
                         (list -20.9502 10.2694) 
                         (list -20.9491 10.2652) 
                         (list -20.9474 10.2613) 
                         (list -20.9452 10.2576) 
                         (list -20.9425 10.2542) 
                         (list -20.9395 10.2512) 
                         (list -20.936 10.2487) 
                         (list -20.9322 10.2466) 
                         (list -20.9282 10.2451) 
                         (list -20.924 10.2442) 
                         (list -20.9197 10.2438) 
                         (list -20.9154 10.244) 
                         (list -20.9112 10.2448) 
                         (list -20.9071 10.2462) 
                         (list -20.9033 10.248) 
                         (list -20.8997 10.2504) 
                         (list -20.8965 10.2533) 
                         (list -20.8937 10.2566) 
                         (list -20.8914 10.2602) 
                         (list -20.8896 10.2641) 
                         (list -20.8883 10.2682) 
                         (list -20.8876 10.2724) 
                         (list -20.8874 10.2755) 
                         (list -20.8874 10.9096) 
                         (list -20.8878 10.9139) 
                         (list -20.8888 10.9181) 
                         (list -20.8903 10.9221) 
                         (list -20.8923 10.9259) 
                         (list -20.8948 10.9293) 
                         (list -20.8978 10.9324) 
                         (list -20.9012 10.9351) 
                         (list -20.9049 10.9373) 
                         (list -20.9088 10.939) 
                         (list -20.913 10.9401) 
                         (list -20.9173 10.9406) 
                         (list -20.9215 10.9406) 
                         (list -20.9258 10.9399) 
                         (list -20.9299 10.9387) 
                         (list -20.9339 10.937) 
                         (list -20.9375 10.9348) 
                         (list -20.9408 10.932) 
                         (list -20.9437 10.9289) 
                         (list -20.9462 10.9254) 
                         (list -20.9482 10.9215) 
                         (list -20.9496 10.9175) 
                         (list -20.9505 10.9133) 
                         (list -20.9508 10.909) 
                         "c"
         )
        (command "pline" (list -22.2492 10.8463) "w" 0 0 
                         (list -22.2553 10.8457) 
                         (list -22.2594 10.8445) 
                         (list -22.2634 10.8429) 
                         (list -22.2671 10.8407) 
                         (list -22.2704 10.838) 
                         (list -22.2734 10.8349) 
                         (list -22.2759 10.8315) 
                         (list -22.278 10.8277) 
                         (list -22.2795 10.8237) 
                         (list -22.2804 10.8195) 
                         (list -22.2808 10.8152) 
                         (list -22.2806 10.8109) 
                         (list -22.2798 10.8067) 
                         (list -22.2785 10.8026) 
                         (list -22.2766 10.7987) 
                         (list -22.2742 10.7952) 
                         (list -22.2713 10.792) 
                         (list -22.2681 10.7892) 
                         (list -22.2645 10.7869) 
                         (list -22.2606 10.785) 
                         (list -22.2565 10.7838) 
                         (list -22.2522 10.7831) 
                         (list -22.2492 10.7829) 
                         (list -21.6156 10.7829) 
                         (list -21.6113 10.7833) 
                         (list -21.6071 10.7842) 
                         (list -21.6031 10.7858) 
                         (list -21.5993 10.7878) 
                         (list -21.5959 10.7903) 
                         (list -21.5928 10.7933) 
                         (list -21.5901 10.7967) 
                         (list -21.5879 10.8004) 
                         (list -21.5862 10.8043) 
                         (list -21.5851 10.8085) 
                         (list -21.5846 10.8127) 
                         (list -21.5846 10.817) 
                         (list -21.5853 10.8213) 
                         (list -21.5865 10.8254) 
                         (list -21.5882 10.8293) 
                         (list -21.5904 10.833) 
                         (list -21.5932 10.8363) 
                         (list -21.5963 10.8392) 
                         (list -21.5999 10.8417) 
                         (list -21.6037 10.8437) 
                         (list -21.6077 10.8451) 
                         (list -21.6119 10.846) 
                         (list -21.6162 10.8463) 
                         "c"
         )
        (command "pline" (list -21.8462 10.4726) "w" 0 0 
                         (list -21.841 10.4694) 
                         (list -21.837 10.4678) 
                         (list -21.8328 10.4668) 
                         (list -21.8285 10.4663) 
                         (list -21.8242 10.4664) 
                         (list -21.82 10.4671) 
                         (list -21.8159 10.4684) 
                         (list -21.812 10.4702) 
                         (list -21.8084 10.4725) 
                         (list -21.8051 10.4753) 
                         (list -21.8022 10.4785) 
                         (list -21.7998 10.482) 
                         (list -21.7979 10.4859) 
                         (list -21.7966 10.4899) 
                         (list -21.7958 10.4942) 
                         (list -21.7955 10.4984) 
                         (list -21.7959 10.5027) 
                         (list -21.7968 10.5069) 
                         (list -21.7983 10.5109) 
                         (list -21.8003 10.5147) 
                         (list -21.8029 10.5182) 
                         (list -21.8058 10.5213) 
                         (list -21.8082 10.5233) 
                         (list -22.2306 10.8403) 
                         (list -22.2343 10.8425) 
                         (list -22.2382 10.8443) 
                         (list -22.2423 10.8455) 
                         (list -22.2466 10.8462) 
                         (list -22.2509 10.8462) 
                         (list -22.2551 10.8457) 
                         (list -22.2593 10.8446) 
                         (list -22.2633 10.8429) 
                         (list -22.267 10.8408) 
                         (list -22.2704 10.8381) 
                         (list -22.2733 10.835) 
                         (list -22.2759 10.8316) 
                         (list -22.2779 10.8278) 
                         (list -22.2795 10.8238) 
                         (list -22.2804 10.8196) 
                         (list -22.2808 10.8153) 
                         (list -22.2806 10.811) 
                         (list -22.2799 10.8068) 
                         (list -22.2785 10.8027) 
                         (list -22.2766 10.7989) 
                         (list -22.2743 10.7953) 
                         (list -22.2714 10.7921) 
                         (list -22.2682 10.7893) 
                         "c"
         )
        (command "pline" (list -22.2682 10.2063) "w" 0 0 
                         (list -22.2727 10.2022) 
                         (list -22.2754 10.1988) 
                         (list -22.2775 10.1951) 
                         (list -22.2792 10.1911) 
                         (list -22.2803 10.187) 
                         (list -22.2808 10.1827) 
                         (list -22.2807 10.1784) 
                         (list -22.2801 10.1742) 
                         (list -22.2789 10.17) 
                         (list -22.2771 10.1661) 
                         (list -22.2748 10.1625) 
                         (list -22.2721 10.1592) 
                         (list -22.2689 10.1563) 
                         (list -22.2654 10.1538) 
                         (list -22.2616 10.1519) 
                         (list -22.2575 10.1505) 
                         (list -22.2533 10.1496) 
                         (list -22.249 10.1493) 
                         (list -22.2447 10.1496) 
                         (list -22.2405 10.1505) 
                         (list -22.2365 10.152) 
                         (list -22.2327 10.154) 
                         (list -22.2301 10.1557) 
                         (list -21.8077 10.473) 
                         (list -21.8045 10.4759) 
                         (list -21.8017 10.4791) 
                         (list -21.7994 10.4828) 
                         (list -21.7976 10.4867) 
                         (list -21.7963 10.4908) 
                         (list -21.7957 10.495) 
                         (list -21.7956 10.4993) 
                         (list -21.796 10.5036) 
                         (list -21.7971 10.5078) 
                         (list -21.7987 10.5117) 
                         (list -21.8008 10.5155) 
                         (list -21.8034 10.5189) 
                         (list -21.8065 10.5219) 
                         (list -21.8099 10.5245) 
                         (list -21.8137 10.5266) 
                         (list -21.8177 10.5282) 
                         (list -21.8218 10.5292) 
                         (list -21.8261 10.5296) 
                         (list -21.8304 10.5295) 
                         (list -21.8346 10.5287) 
                         (list -21.8387 10.5274) 
                         (list -21.8426 10.5256) 
                         (list -21.8462 10.5233) 
                         "c"
         )
        (command "pline" (list -21.6162 10.1493) "w" 0 0 
                         (list -21.6101 10.1499) 
                         (list -21.606 10.151) 
                         (list -21.602 10.1527) 
                         (list -21.5983 10.1549) 
                         (list -21.5949 10.1575) 
                         (list -21.592 10.1606) 
                         (list -21.5894 10.1641) 
                         (list -21.5874 10.1679) 
                         (list -21.5859 10.1719) 
                         (list -21.5849 10.1761) 
                         (list -21.5845 10.1804) 
                         (list -21.5848 10.1847) 
                         (list -21.5855 10.1889) 
                         (list -21.5869 10.193) 
                         (list -21.5888 10.1968) 
                         (list -21.5912 10.2004) 
                         (list -21.594 10.2036) 
                         (list -21.5973 10.2064) 
                         (list -21.6009 10.2087) 
                         (list -21.6048 10.2105) 
                         (list -21.6089 10.2118) 
                         (list -21.6131 10.2125) 
                         (list -21.6162 10.2127) 
                         (list -22.2498 10.2127) 
                         (list -22.2541 10.2123) 
                         (list -22.2582 10.2113) 
                         (list -22.2623 10.2098) 
                         (list -22.266 10.2078) 
                         (list -22.2695 10.2053) 
                         (list -22.2726 10.2023) 
                         (list -22.2753 10.1989) 
                         (list -22.2775 10.1952) 
                         (list -22.2791 10.1913) 
                         (list -22.2802 10.1871) 
                         (list -22.2808 10.1828) 
                         (list -22.2807 10.1785) 
                         (list -22.2801 10.1743) 
                         (list -22.2789 10.1702) 
                         (list -22.2772 10.1662) 
                         (list -22.2749 10.1626) 
                         (list -22.2722 10.1593) 
                         (list -22.269 10.1563) 
                         (list -22.2655 10.1539) 
                         (list -22.2617 10.1519) 
                         (list -22.2576 10.1505) 
                         (list -22.2534 10.1496) 
                         (list -22.2492 10.1493) 
                         "c"
         )
        (command "pline" (list -21.9645 11.1315) "w" 0 0 
                         (list -21.9639 11.1254) 
                         (list -21.9628 11.1213) 
                         (list -21.9611 11.1173) 
                         (list -21.959 11.1136) 
                         (list -21.9563 11.1103) 
                         (list -21.9532 11.1073) 
                         (list -21.9497 11.1047) 
                         (list -21.946 11.1027) 
                         (list -21.9419 11.1012) 
                         (list -21.9377 11.1002) 
                         (list -21.9335 11.0999) 
                         (list -21.9292 11.1001) 
                         (list -21.9249 11.1009) 
                         (list -21.9209 11.1022) 
                         (list -21.917 11.1041) 
                         (list -21.9134 11.1065) 
                         (list -21.9102 11.1094) 
                         (list -21.9074 11.1126) 
                         (list -21.9051 11.1162) 
                         (list -21.9033 11.1201) 
                         (list -21.902 11.1242) 
                         (list -21.9013 11.1285) 
                         (list -21.9012 11.1315) 
                         (list -21.9012 11.7657) 
                         (list -21.9016 11.77) 
                         (list -21.9025 11.7742) 
                         (list -21.904 11.7782) 
                         (list -21.9061 11.782) 
                         (list -21.9086 11.7855) 
                         (list -21.9116 11.7886) 
                         (list -21.9149 11.7912) 
                         (list -21.9186 11.7934) 
                         (list -21.9226 11.7951) 
                         (list -21.9267 11.7962) 
                         (list -21.931 11.7967) 
                         (list -21.9353 11.7967) 
                         (list -21.9396 11.7961) 
                         (list -21.9437 11.7949) 
                         (list -21.9476 11.7931) 
                         (list -21.9513 11.7909) 
                         (list -21.9546 11.7882) 
                         (list -21.9575 11.785) 
                         (list -21.96 11.7815) 
                         (list -21.9619 11.7777) 
                         (list -21.9634 11.7736) 
                         (list -21.9642 11.7694) 
                         (list -21.9645 11.7651) 
                         "c"
         )
  
  (command "layer" "n" "f" "")
  (command "chprop" "all" "" "la" "f" "")
  (command "layer" "c" "5" "f" "")
  (command "layer" "s" "f" "")
  (prin1)
  (setvar "osmode" oldosmode)
  (setvar "orthomode" oldorthomode)
 
  )
(prompt "\n 请输入szhcfm运行程序")
(prompt "\n 此程序为苏州鸿测的边框图形")
