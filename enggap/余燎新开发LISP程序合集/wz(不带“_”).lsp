(defun c:wz ()
  (setq xn (getreal "\n X方向的排版个数:"))
  (setq yn (getreal "\n Y方向的排版个数:"))
  (setq x_val (getreal "\n X方向的排版尺寸:"))
  (setq y_val (getreal "\n Y方向的排版尺寸:"))
  (setq f_point (getpoint "\n 请点取矩形左下角的端点:"))
  (setq ang (getangle "\n 旋转角度: (90/0)"))
  (setq angl (* 180 (/ ang pi)))
  (setq num (getint "\n 请选择图形单粒的个数：(1/2)"))
  (setq x_f (car f_point))
  (setq y_f (cadr f_point))
  (setq xm (fix xn))
  (setq ym (fix yn))
  (command "-style" "black" "arial" "0.6"	"0.6" "" "" "")
  (if (= num 1)
    (progn
;;;                                     有一个单粒，文字不旋转   
      (if (= ang 0)
	(progn
	  (setq x1_f (+ x_f 0.1))
	  (setq y1_f (+ y_f 0.1))
	  (setq n1 65)
	  (setq f1_point (list x1_f y1_f))
	  (repeat ym
	    (setq m 1)
	    (repeat xm
	      (setq asc (chr n1))
	      (setq zf (strcat asc (strcat "" (itoa m))))
	      (command "text" f1_point angl zf)
	      (setq x1_f (+ x1_f x_val))
	      (setq f1_point (list x1_f y1_f))
	      (setq m (+ m 1))
	    )
	    (setq x1_f (+ x_f 0.1))
	    (setq y1_f (+ y1_f y_val))
	    (setq f1_point (list x1_f y1_f))
	    (setq n1 (+ n1 1))
	  )
	)
      )
;;;                                        有一个单粒，文字旋转
      (if (= angl 90)
	(progn
	  (setq x1_f (+ x_f 0.7))
	  (setq y1_f (+ y_f 0.1))
	  (progn
	    (setq n1 65)
	    (setq f1_point (list x1_f y1_f))
	    (repeat ym
	      (setq m 1)
	      (repeat xm
		(setq asc (chr n1))
		(setq zf (strcat asc (strcat "" (itoa m))))
		(command "text" f1_point angl zf)
		(setq x1_f (+ x1_f x_val))
		(setq f1_point (list x1_f y1_f))
		(setq m (+ m 1))
	      )
	      (setq x1_f (+ x_f 0.7))
	      (setq y1_f (+ y1_f y_val))
	      (setq f1_point (list x1_f y1_f))
	      (setq n1 (+ n1 1))
	    )
	  )
	)
      )
    )
  )
  (if (= num 2)
    (progn
      (setq pf (getstring "\n 两个单立是横排(h/H)或竖排(s/S): "))
      (setq s_point (getpoint "请点取第二个框的左下角端点 :"))
      (setq x_s (car s_point))
      (setq y_s (cadr s_point))
;;;                                          有两个单粒且两单粒是横排，不旋转
      (if (or (= pf "h") (= pf "H"))
	(progn
	  (if (= angl 0)
	    (progn
	      (setq x1_f (+ x_f 0.1))
	      (setq y1_f (+ y_f 0.1))
	      (setq x1_s (+ x_s 0.1))
	      (setq y1_s (+ y_s 0.1))
	      (setq n1 65)
	      (setq f1_point (list x1_f y1_f))
	      (repeat ym
		(setq m 1)
		(if (= xm xn)
		  (repeat xm
		    (setq asc (chr n1))
		    (setq zf (strcat asc (strcat "" (itoa m))))
		    (command "text" f1_point angl zf)
		    (setq x1_f (+ x1_f x_val))
		    (setq f1_point (list x1_f y1_f))
		    (setq m (+ m 2))
		  )
		  (repeat (+ xm 1)
		    (setq asc (chr n1))
		    (setq zf (strcat asc (strcat "" (itoa m))))
		    (command "text" f1_point angl zf)
		    (setq x1_f (+ x1_f x_val))
		    (setq f1_point (list x1_f y1_f))
		    (setq m (+ m 2))
		  )
		)
		(setq x1_f (+ x_f 0.1))
		(setq y1_f (+ y1_f y_val))
		(setq f1_point (list x1_f y1_f))
		(setq n1 (+ n1 1))
	      )
	      (setq n1 65)
	      (setq s1_point (list x1_s y1_s))
	      (repeat ym
		(setq m 2)
		(repeat	xm
		  (setq asc (chr n1))
		  (setq zf (strcat asc (strcat "" (itoa m))))
		  (command "text" s1_point angl zf)
		  (setq x1_s (+ x1_s x_val))
		  (setq s1_point (list x1_s y1_s))
		  (setq m (+ m 2))
		)
		(setq x1_s (+ x_s 0.1))
		(setq y1_s (+ y1_s y_val))
		(setq s1_point (list x1_s y1_s))
		(setq n1 (+ n1 1))
	      )
	    )
	  )
	  (if (= angl 90)
	    (progn
	      (setq n1 65)
	      (setq s1_point (list x1_s y1_s))
	      (setq x1_f (+ x_f 0.7))
	      (setq y1_f (+ y_f 0.1))
	      (setq x1_s (+ x_s 0.7))
	      (setq y1_s (+ y_s 0.1))
	      (setq n1 65)
	      (setq f1_point (list x1_f y1_f))
	      (repeat ym
		(setq m 1)
		(if (= xm xn)
		  (repeat xm
		    (setq asc (chr n1))
		    (setq zf (strcat asc (strcat "" (itoa m))))
		    (command "text" f1_point angl zf)
		    (setq x1_f (+ x1_f x_val))
		    (setq f1_point (list x1_f y1_f))
		    (setq m (+ m 2))
		  )
		  (repeat (+ xm 1)
		    (setq asc (chr n1))
		    (setq zf (strcat asc (strcat "" (itoa m))))
		    (command "text" f1_point angl zf)
		    (setq x1_f (+ x1_f x_val))
		    (setq f1_point (list x1_f y1_f))
		    (setq m (+ m 2))
		  )
		)
		(setq x1_f (+ x_f 0.7))
		(setq y1_f (+ y1_f y_val))
		(setq f1_point (list x1_f y1_f))
		(setq n1 (+ n1 1))
	      )
	      (setq n1 65)
	      (setq s1_point (list x1_s y1_s))
	      (repeat ym
		(setq m 2)
		(repeat	xm
		  (setq asc (chr n1))
		  (setq zf (strcat asc (strcat "" (itoa m))))
		  (command "text" s1_point angl zf)
		  (setq x1_s (+ x1_s x_val))
		  (setq s1_point (list x1_s y1_s))
		  (setq m (+ m 2))
		)
		(setq x1_s (+ x_s 0.7))
		(setq y1_s (+ y1_s y_val))
		(setq s1_point (list x1_s y1_s))
		(setq n1 (+ n1 1))
	      )
	    )
	  )
	)
      )
;;;                                             两个单粒为竖排，不旋转  
      (if (or (= pf "s") (= pf "S"))
	(progn
	  (if (= angl 0)
	    (progn
	      (setq x1_f (+ x_f 0.1))
	      (setq y1_f (+ y_f 0.1))
	      (setq x1_s (+ x_s 0.1))
	      (setq y1_s (+ y_s 0.1))
	      (setq n1 65)
	      (setq f1_point (list x1_f y1_f))
	      (if (= yn ym)
		(repeat	ym
		  (setq m 1)
		  (repeat xm
		    (setq asc (chr n1))
		    (setq zf (strcat asc (strcat "" (itoa m))))
		    (command "text" f1_point angl zf)
		    (setq x1_f (+ x1_f x_val))
		    (setq f1_point (list x1_f y1_f))
		    (setq m (+ m 1))
		  )
		  (setq x1_f (+ x_f 0.1))
		  (setq y1_f (+ y1_f y_val))
		  (setq f1_point (list x1_f y1_f))
		  (setq n1 (+ n1 2))
		)
		(repeat	(+ ym 1)
		  (setq m 1)
		  (repeat xm
		    (setq asc (chr n1))
		    (setq zf (strcat asc (strcat "" (itoa m))))
		    (command "text" f1_point angl zf)
		    (setq x1_f (+ x1_f x_val))
		    (setq f1_point (list x1_f y1_f))
		    (setq m (+ m 1))
		  )
		  (setq x1_f (+ x_f 0.1))
		  (setq y1_f (+ y1_f y_val))
		  (setq f1_point (list x1_f y1_f))
		  (setq n1 (+ n1 2))
		)
	      )
	      (setq n1 66)
	      (setq s1_point (list x1_s y1_s))
	      (repeat ym
		(setq m 1)
		(repeat	xm
		  (setq asc (chr n1))
		  (setq zf (strcat asc (strcat "" (itoa m))))
		  (command "text" s1_point angl zf)
		  (setq x1_s (+ x1_s x_val))
		  (setq s1_point (list x1_s y1_s))
		  (setq m (+ m 1))
		)
		(setq x1_s (+ x_s 0.1))
		(setq y1_s (+ y1_s y_val))
		(setq s1_point (list x1_s y1_s))
		(setq n1 (+ n1 2))
	      )
	    )
	  )
;;;                                               两个单粒为竖排但旋转
	  (if (= angl 90)
	    (progn
	      (setq x1_f (+ x_f 0.7))
	      (setq y1_f (+ y_f 0.1))
	      (setq x1_s (+ x_s 0.7))
	      (setq y1_s (+ y_s 0.1))
	      (setq n1 65)
	      (setq f1_point (list x1_f y1_f))
	      (if (= yn ym)
		(repeat	ym
		  (setq m 1)
		  (repeat xm
		    (setq asc (chr n1))
		    (setq zf (strcat asc (strcat "" (itoa m))))
		    (command "text" f1_point angl zf)
		    (setq x1_f (+ x1_f x_val))
		    (setq f1_point (list x1_f y1_f))
		    (setq m (+ m 1))
		  )
		  (setq x1_f (+ x_f 0.7))
		  (setq y1_f (+ y1_f y_val))
		  (setq f1_point (list x1_f y1_f))
		  (setq n1 (+ n1 2))
		)
		(repeat	(+ ym 1)
		  (setq m 1)
		  (repeat xm
		    (setq asc (chr n1))
		    (setq zf (strcat asc (strcat "" (itoa m))))
		    (command "text" f1_point angl zf)
		    (setq x1_f (+ x1_f x_val))
		    (setq f1_point (list x1_f y1_f))
		    (setq m (+ m 1))
		  )
		  (setq x1_f (+ x_f 0.7))
		  (setq y1_f (+ y1_f y_val))
		  (setq f1_point (list x1_f y1_f))
		  (setq n1 (+ n1 2))
		)
	      )
	      (setq n1 66)
	      (setq s1_point (list x1_s y1_s))
	      (repeat ym
		(setq m 1)
		(repeat	xm
		  (setq asc (chr n1))
		  (setq zf (strcat asc (strcat "" (itoa m))))
		  (command "text" s1_point angl zf)
		  (setq x1_s (+ x1_s x_val))
		  (setq s1_point (list x1_s y1_s))
		  (setq m (+ m 1))
		)
		(setq x1_s (+ x_s 0.7))
		(setq y1_s (+ y1_s y_val))
		(setq s1_point (list x1_s y1_s))
		(setq n1 (+ n1 2))
	      )
	    )
	  )
	)
      )
    )
  )
)
