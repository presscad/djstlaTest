(defun c:gw ()
  (defun dg ()
    (command "pline" (list -198.95 150.25) "w" 0 0 
                         (list -198.95 150.05) 
                         (list -199.95 150.05) 
                         (list -199.95 151.05) 
                         (list -199.75 151.05) 
                         (list -199.75 150.25) 
                         "c"
         )
        (command "pline" (list -200.25 150.25) "w" 0 0 
                         (list -201.05 150.25) 
                         (list -201.05 150.05) 
                         (list -200.05 150.05) 
                         (list -200.05 151.05) 
                         (list -200.25 151.05) 
                         "c"
         )
        (command "pline" (list -198.95 149.75) "w" 0 0 
                         (list -199.75 149.75) 
                         (list -199.75 148.95) 
                         (list -199.95 148.95) 
                         (list -199.95 149.95) 
                         (list -198.95 149.95) 
                         "c"
         )
        (command "pline" (list -200.25 149.75) "w" 0 0 
                         (list -200.25 148.95) 
                         (list -200.05 148.95) 
                         (list -200.05 149.95) 
                         (list -201.05 149.95) 
                         (list -201.05 149.75) 
                         "c"
         )
        (command "pline" (list 202.5 0.5) "w" 0 0 
                         (list 202.5 0.0) 
                         (list 203.0 0.0) 
                         (list 203.0 0.5) 
                         "c"
         )
        (command "pline" (list 202.5 0.0) "w" 0 0 
                         (list 202.5 -0.5) 
                         (list 202.0 -0.5) 
                         (list 202.0 0.0) 
                         "c"
         )
        (command "pline" (list -202.0 0.5) "w" 0 0 
                         (list -202.0 0.0) 
                         (list -202.5 0.0) 
                         (list -202.5 0.5) 
                         "c"
         )
        (command "pline" (list -203.0 0.0) "w" 0 0 
                         (list -203.0 -0.5) 
                         (list -202.5 -0.5) 
                         (list -202.5 0.0) 
                         "c"
         )
;draw plus on the top and bottom
    
        (command "pline" (list 0.2 155.1) "w" 0 0 
                         (list 0.2 156.9) 
                         (list -0.2 156.9) 
                         (list -0.2 155.1)
		 	 (list -2 155.1)
			 (list -2 154.7)
			 (list -0.2 154.7)
			 (list -0.2 152.9)
			 (list 0.2 152.9)
			 (list 0.2 154.7)
			 (list 2 154.7)
			 (list 2 155.1)
                         "c"
         )

        (command "pline" (list 0.2 -154.7) "w" 0 0 
                         (list 0.2 -152.9) 
                         (list -0.2 -152.9) 
                         (list -0.2 -154.7)
		 	 (list -2 -154.7)
			 (list -2 -155.1)
			 (list -0.2 -155.1)
			 (list -0.2 -156.9)
			 (list 0.2 -156.9)
			 (list 0.2 -155.1)
			 (list 2 -155.1)
			 (list 2 -154.7)
                         "c"
         )

       
        (command "pline" (list 210.685 91.5984) "w" 0 0 
                         (list 210.623 91.6292) 
                         (list 210.543 91.6046) 
                         (list 210.518 91.4442) 
                         (list 210.444 91.401) 
                         (list 210.302 91.401) 
                         (list 210.191 91.3825) 
                         (list 210.05 91.3579) 
                         (list 209.932 91.3209) 
                         (list 209.828 91.2284) 
                         (list 209.76 91.1297) 
                         (list 209.674 90.9693) 
                         (list 209.637 90.809) 
                         (list 209.612 90.735) 
                         (list 209.6 90.5685) 
                         (list 209.581 90.4575) 
                         (list 209.575 90.439) 
                         (list 209.563 90.5376) 
                         (list 209.55 90.6733) 
                         (list 209.526 90.8645) 
                         (list 209.489 91.0248) 
                         (list 209.427 91.2099) 
                         (list 209.322 91.3702) 
                         (list 209.224 91.4442) 
                         (list 209.039 91.5182) 
                         (list 208.909 91.4874) 
                         (list 208.804 91.3949) 
                         (list 208.73 91.2777) 
                         (list 208.727 91.2697) 
                         (list 209.077 90.5599) 
                         (list 209.291 90.5635) 
                         (list 209.365 90.5389) 
                         (list 209.396 90.5142) 
                         (list 209.458 90.4464) 
                         (list 209.47 90.3847) 
                         (list 209.482 90.3168) 
                         (list 209.489 90.1503) 
                         (list 209.476 89.7495) 
                         (list 209.445 89.7125) 
                         (list 208.724 89.7248) 
                         (list 208.706 89.7495) 
                         (list 208.706 90.3045) 
                         (list 208.718 90.4094) 
                         (list 208.755 90.471) 
                         (list 208.798 90.5019) 
                         (list 208.854 90.5204) 
                         (list 208.891 90.5389) 
                         (list 208.928 90.5574) 
                         (list 209.077 90.5599) 
                         (list 208.727 91.2697) 
                         (list 208.656 91.0927) 
                         (list 208.638 91.0372) 
                         (list 208.601 90.7288) 
                         (list 208.601 90.587) 
                         (list 208.576 90.3341) 
                         (list 208.564 89.8839) 
                         (list 208.576 88.5641) 
                         (list 208.582 88.5148) 
                         (list 208.693 88.5086) 
                         (list 208.706 88.5641) 
                         (list 208.712 88.8725) 
                         (list 210.543 88.891) 
                         (list 210.537 88.5826) 
                         (list 210.235 88.5888) 
                         (list 210.154 88.5888) 
                         (list 210.142 88.6135) 
                         (list 209.969 88.6011) 
                         (list 209.957 88.558) 
                         (list 209.951 88.4346) 
                         (list 210.105 88.3729) 
                         (list 210.241 88.2989) 
                         (list 210.364 88.1756) 
                         (list 210.444 88.0831) 
                         (list 210.475 88.0029) 
                         (list 210.506 87.8611) 
                         (list 210.555 87.7192) 
                         (list 210.555 87.4417) 
                         (list 210.549 86.9372) 
                         (list 210.512 86.9064) 
                         (list 209.655 86.9002) 
                         (list 209.686 87.0297) 
                         (list 209.711 87.1716) 
                         (list 209.741 87.3319) 
                         (list 209.791 87.4738) 
                         (list 209.865 87.5231) 
                         (list 209.939 87.5601) 
                         (list 210.062 87.5663) 
                         (list 210.08 87.5971) 
                         (list 210.087 87.7575) 
                         (list 210.062 87.7698) 
                         (list 209.156 87.7636) 
                         (list 209.143 87.7328) 
                         (list 209.15 87.5848) 
                         (list 209.168 87.5539) 
                         (list 209.248 87.5416) 
                         (list 209.31 87.5293) 
                         (list 209.378 87.5046) 
                         (list 209.415 87.4429) 
                         (list 209.47 87.3751) 
                         (list 209.495 87.3443) 
                         (list 209.507 87.2147) 
                         (list 209.513 87.1284) 
                         (list 209.513 86.9064) 
                         (list 208.706 86.9064) 
                         (list 208.7 87.2086) 
                         (list 208.712 87.3751) 
                         (list 208.712 87.6218) 
                         (list 208.737 87.7451) 
                         (list 208.761 87.8561) 
                         (list 208.798 87.9425) 
                         (list 208.866 88.0226) 
                         (list 208.971 88.1152) 
                         (list 209.032 88.1768) 
                         (list 209.113 88.2385) 
                         (list 209.15 88.294) 
                         (list 209.162 88.3742) 
                         (list 209.15 88.4544) 
                         (list 209.051 88.4544) 
                         (list 208.576 88.4544) 
                         (list 208.582 85.7346) 
                         (list 208.613 85.7223) 
                         (list 208.687 85.7285) 
                         (list 208.724 85.7531) 
                         (list 208.724 86.0615) 
                         (list 210.537 86.0615) 
                         (list 210.549 85.6914) 
                         (list 210.592 85.6791) 
                         (list 210.666 85.6729) 
                         (list 210.678 85.7223) 
                         (list 210.666 90.1565) 
                         (list 210.641 90.175) 
                         (list 210.555 90.1688) 
                         (list 210.537 90.1503) 
                         (list 210.53 89.7495) 
                         (list 209.637 89.731) 
                         (list 209.618 89.7495) 
                         (list 209.63 89.9715) 
                         (list 209.643 90.0948) 
                         (list 209.674 90.1873) 
                         (list 209.723 90.286) 
                         (list 209.772 90.3415) 
                         (list 209.871 90.397) 
                         (list 209.926 90.4279) 
                         (list 210.025 90.4402) 
                         (list 210.167 90.4587) 
                         (list 210.284 90.4649) 
                         (list 210.438 90.508) 
                         (list 210.506 90.5759) 
                         (list 210.586 90.6745) 
                         (list 210.648 90.8164) 
                         (list 210.691 90.9829) 
                         (list 210.709 91.0754) 
                         (list 210.697 91.5935) 
                         "c"
         )
        (command "pline" (list 208.595 83.0378) "w" 0 0 
                         (list 208.718 83.044) 
                         (list 208.724 83.1735) 
                         (list 208.737 83.2413) 
                         (list 210.543 83.2475) 
                         (list 210.567 83.229) 
                         (list 210.567 82.8713) 
                         (list 210.592 82.859) 
                         (list 210.672 82.859) 
                         (list 210.691 82.8898) 
                         (list 210.703 82.933) 
                         (list 210.697 84.5179) 
                         (list 210.672 84.555) 
                         (list 210.586 84.5611) 
                         (list 210.549 84.5241) 
                         (list 210.543 84.0986) 
                         (list 209.834 84.0924) 
                         (list 209.766 84.1047) 
                         (list 209.741 84.1232) 
                         (list 209.741 84.1849) 
                         (list 209.735 84.2651) 
                         (list 209.735 84.3329) 
                         (list 209.729 84.5981) 
                         (list 209.723 84.8078) 
                         (list 209.729 85.036) 
                         (list 209.698 85.1717) 
                         (list 209.661 85.3875) 
                         (list 209.6 85.554) 
                         (list 209.501 85.7206) 
                         (list 209.402 85.8192) 
                         (list 209.291 85.8871) 
                         (list 209.217 85.8932) 
                         (list 209.113 85.9056) 
                         (list 209.002 85.8686) 
                         (list 208.909 85.8254) 
                         (list 208.823 85.7576) 
                         (list 208.749 85.6157) 
                         (list 208.687 85.4924) 
                         (list 208.656 85.3444) 
                         (list 208.638 85.184) 
                         (list 208.633 85.1083) 
                         (list 208.73 84.0801) 
                         (list 208.724 84.3514) 
                         (list 208.712 84.5056) 
                         (list 208.724 84.6968) 
                         (list 208.774 84.8386) 
                         (list 208.854 84.9065) 
                         (list 208.952 84.9497) 
                         (list 209.063 84.9682) 
                         (list 209.199 84.962) 
                         (list 209.31 84.9743) 
                         (list 209.409 84.9497) 
                         (list 209.433 84.9497) 
                         (list 209.55 84.8818) 
                         (list 209.587 84.8078) 
                         (list 209.6 84.7585) 
                         (list 209.6 84.6105) 
                         (list 209.6 84.0986) 
                         (list 209.581 84.0986) 
                         (list 208.73 84.0801) 
                         (list 208.633 85.1083) 
                         (list 208.626 84.9928) 
                         (list 208.601 84.8201) 
                         (list 208.595 84.6166) 
                         (list 208.582 84.4008) 
                         "c"
         )
        (command "pline" (list 210.524 93.8556) "w" 0 0 
                         (list 210.537 93.8062) 
                         (list 210.635 93.8124) 
                         (list 210.648 93.8741) 
                         (list 210.648 95.4406) 
                         (list 210.623 95.4837) 
                         (list 210.524 95.4837) 
                         (list 210.512 95.4036) 
                         (list 210.512 95.052) 
                         (list 208.687 95.0335) 
                         (list 208.693 95.3974) 
                         (list 208.656 95.4591) 
                         (list 208.576 95.4652) 
                         (list 208.552 95.4406) 
                         (list 208.539 95.3851) 
                         (list 208.546 94.1146) 
                         (list 209.686 93.5534) 
                         (list 209.704 93.5287) 
                         (list 208.552 92.949) 
                         (list 208.558 91.5614) 
                         (list 208.675 91.5491) 
                         (list 208.7 91.6046) 
                         (list 208.7 91.9746) 
                         (list 210.401 91.9808) 
                         (list 210.456 91.9684) 
                         (list 210.518 91.9376) 
                         (list 210.53 91.8451) 
                         (list 210.549 91.7526) 
                         (list 210.623 91.7526) 
                         (list 210.648 91.7649) 
                         (list 210.66 92.5975) 
                         (list 210.635 92.6283) 
                         (list 210.567 92.6283) 
                         (list 210.53 92.6036) 
                         (list 210.524 92.2583) 
                         (list 210.469 92.2213) 
                         (list 210.407 92.1966) 
                         (list 208.792 92.1781) 
                         (list 208.798 92.1966) 
                         (list 210.592 93.0539) 
                         (list 210.648 93.1032) 
                         (list 210.641 93.2944) 
                         (list 208.823 94.1701) 
                         (list 208.774 94.2009) 
                         (list 208.841 94.2256) 
                         (list 210.493 94.2318) 
                         (list 210.518 94.2256) 
                         (list 210.524 93.8988) 
                         "c"
         )
        (command "pline" (list 207.95 76.8674) "w" 0 0 
                         (list 207.974 76.8985) 
                         (list 207.935 77.0077) 
                         (list 207.031 79.1587) 
                         (list 207.008 79.0574) 
                         (list 207.008 78.9482) 
                         (list 207.732 77.2181) 
                         (list 207.787 77.2103) 
                         (list 207.935 76.8518) 
                         "c"
         )
        (command "pline" (list 208.418 76.4621) "w" 0 0 
                         (list 208.425 76.5245) 
                         (list 207.085 79.673) 
                         (list 207.047 79.5328) 
                         (list 207.054 79.3535) 
                         (list 207.21 79.0184) 
                         (list 207.241 79.0418) 
                         (list 207.974 77.2804) 
                         (list 208.036 77.2726) 
                         (list 208.386 76.4621) 
                         "c"
         )
        (command "pline" (list 208.807 76.2127) "w" 0 0 
                         (list 208.776 76.3452) 
                         (list 207.179 80.0939) 
                         (list 207.14 79.9692) 
                         (list 207.124 79.8211) 
                         (list 207.132 79.7822) 
                         (list 207.444 79.0807) 
                         (list 207.553 79.034) 
                         (list 208.277 77.2726) 
                         (list 208.386 77.0934) 
                         (list 208.752 76.2361) 
                         (list 208.791 76.1971) 
                         "c"
         )
        (command "pline" (list 209.158 76.0568) "w" 0 0 
                         (list 209.158 76.1582) 
                         (list 209.126 76.2751) 
                         (list 207.311 80.4056) 
                         (list 207.272 80.2809) 
                         (list 207.272 80.164) 
                         (list 207.748 79.0574) 
                         (list 207.81 79.0574) 
                         (list 208.55 77.2804) 
                         (list 208.589 77.2493) 
                         (list 208.643 77.1557) 
                         (list 209.134 76.0335) 
                         "c"
         )
        (command "pline" (list 209.493 75.9867) "w" 0 0 
                         (list 207.491 80.6862) 
                         (list 207.42 80.6161) 
                         (list 207.413 80.4992) 
                         (list 207.428 80.4368) 
                         (list 207.997 79.1665) 
                         (list 208.036 79.1041) 
                         (list 208.106 79.0729) 
                         (list 208.83 77.3194) 
                         (list 208.877 77.296) 
                         (list 209.446 75.9555) 
                         "c"
         )
        (command "pline" (list 209.796 75.9088) "w" 0 0 
                         (list 209.804 76.0101) 
                         (list 207.662 80.9278) 
                         (list 207.607 80.8499) 
                         (list 207.6 80.7252) 
                         (list 208.301 79.0807) 
                         (list 208.363 79.1197) 
                         (list 209.095 77.3194) 
                         (list 209.142 77.2804) 
                         (list 209.197 77.1869) 
                         (list 209.75 75.9166) 
                         "c"
         )
        (command "pline" (list 210.085 75.9321) "w" 0 0 
                         (list 207.864 81.185) 
                         (list 207.787 81.0993) 
                         (list 207.748 81.0135) 
                         (list 208.589 79.0729) 
                         (list 208.628 79.1275) 
                         (list 209.376 77.3817) 
                         (list 209.446 77.2882) 
                         (list 210.053 75.8932) 
                         "c"
         )
        (command "pline" (list 211.801 76.3296) "w" 0 0 
                         (list 211.746 76.3998) 
                         (list 210.811 78.5975) 
                         (list 210.843 78.6209) 
                         (list 210.882 78.5897) 
                         (list 210.991 78.3248) 
                         (list 211.053 78.1845) 
                         (list 211.115 78.1767) 
                         (list 211.326 77.6467) 
                         (list 211.318 77.5922) 
                         (list 211.357 77.6) 
                         (list 211.38 77.6623) 
                         (list 211.396 77.4909) 
                         (list 211.809 76.5167) 
                         "c"
         )
        (command "pline" (list 211.754 75.7295) "w" 0 0 
                         (list 210.414 78.8703) 
                         (list 210.391 78.8937) 
                         (list 210.375 78.9716) 
                         (list 210.422 78.9638) 
                         (list 210.469 78.9405) 
                         (list 210.78 78.1845) 
                         (list 210.866 78.1611) 
                         (list 211.357 76.9687) 
                         (list 211.365 76.9453) 
                         (list 211.396 77.0077) 
                         (list 211.396 76.8206) 
                         (list 211.536 76.4699) 
                         (list 211.544 76.4076) 
                         (list 211.598 76.3842) 
                         (list 211.653 76.3764) 
                         (list 211.793 76.0491) 
                         (list 211.793 75.901) 
                         "c"
         )
        (command "pline" (list 211.629 75.371) "w" 0 0 
                         (list 210.017 79.1898) 
                         (list 210.048 79.2054) 
                         (list 210.079 79.221) 
                         (list 210.523 78.1299) 
                         (list 210.554 78.1143) 
                         (list 211.053 76.9375) 
                         (list 211.294 76.353) 
                         (list 211.326 76.3452) 
                         (list 211.365 76.3452) 
                         (list 211.396 76.3686) 
                         (list 211.411 76.2127) 
                         (list 211.692 75.6204) 
                         (list 211.715 75.5113) 
                         (list 211.7 75.4645) 
                         "c"
         )
        (command "pline" (list 211.489 75.0203) "w" 0 0 
                         (list 209.659 79.3301) 
                         (list 209.666 79.3535) 
                         (list 209.69 79.3769) 
                         (list 209.729 79.3613) 
                         (list 210.227 78.1533) 
                         (list 210.258 78.1377) 
                         (list 211.006 76.3608) 
                         (list 211.053 76.3686) 
                         (list 211.31 75.8152) 
                         (list 211.333 75.6905) 
                         (list 211.357 75.6672) 
                         (list 211.372 75.7373) 
                         (list 211.404 75.7061) 
                         (list 211.396 75.6048) 
                         (list 211.396 75.5892) 
                         (list 211.528 75.3165) 
                         (list 211.567 75.145) 
                         (list 211.497 75.0359) 
                         "c"
         )
        (command "pline" (list 211.333 74.7631) "w" 0 0 
                         (list 209.355 79.3613) 
                         (list 209.347 79.4159) 
                         (list 209.37 79.447) 
                         (list 209.955 78.1065) 
                         (list 210.001 78.1143) 
                         (list 210.726 76.353) 
                         (list 210.796 76.3608) 
                         (list 211.349 75.0593) 
                         (list 211.38 75.0904) 
                         (list 211.404 74.919) 
                         (list 211.396 74.8488) 
                         "c"
         )
        (command "pline" (list 211.256 74.6072) "w" 0 0 
                         (list 211.178 74.5137) 
                         (list 211.162 74.4981) 
                         (list 209.043 79.4314) 
                         (list 209.043 79.4938) 
                         (list 209.09 79.5172) 
                         (list 209.604 78.2936) 
                         (list 209.666 78.1065) 
                         (list 209.736 78.1065) 
                         (list 210.461 76.314) 
                         (list 210.523 76.314) 
                         "c"
         )
        (command "pline" (list 210.991 74.3033) "w" 0 0 
                         (list 208.739 79.486) 
                         (list 208.786 79.5172) 
                         (list 208.817 79.486) 
                         (list 209.409 78.091) 
                         (list 209.472 78.0832) 
                         (list 210.188 76.3218) 
                         (list 210.266 76.2907) 
                         (list 211.061 74.389) 
                         "c"
         )
        (command "pline" (list 208.619 79.7569) "w" 0 0 
                         (list 208.601 79.8617) 
                         (list 208.595 81.348) 
                         (list 208.638 81.4158) 
                         (list 208.73 81.4097) 
                         (list 208.743 81.385) 
                         (list 208.743 80.978) 
                         (list 210.05 80.978) 
                         (list 210.13 80.9903) 
                         (list 210.265 81.0088) 
                         (list 210.339 81.0458) 
                         (list 210.456 81.0828) 
                         (list 210.543 81.1877) 
                         (list 210.586 81.3357) 
                         (list 210.592 81.4528) 
                         (list 210.604 81.6502) 
                         (list 210.592 81.8044) 
                         (list 210.574 81.9709) 
                         (list 210.543 82.0942) 
                         (list 210.493 82.2299) 
                         (list 210.389 82.3348) 
                         (list 210.259 82.3964) 
                         (list 210.198 82.4088) 
                         (list 210.031 82.4149) 
                         (list 209.686 82.4088) 
                         (list 208.829 82.4088) 
                         (list 208.774 82.3964) 
                         (list 208.749 82.3594) 
                         (list 208.737 82.3409) 
                         (list 208.749 82.0757) 
                         (list 208.718 82.0079) 
                         (list 208.607 82.0079) 
                         (list 208.601 82.0572) 
                         (list 208.589 82.859) 
                         (list 208.644 82.8775) 
                         (list 208.712 82.8775) 
                         (list 208.743 82.785) 
                         (list 208.755 82.6925) 
                         (list 208.804 82.6616) 
                         (list 208.854 82.6493) 
                         (list 208.915 82.6431) 
                         (list 210.167 82.6616) 
                         (list 210.284 82.6431) 
                         (list 210.358 82.6061) 
                         (list 210.45 82.5506) 
                         (list 210.524 82.4889) 
                         (list 210.574 82.4026) 
                         (list 210.641 82.2361) 
                         (list 210.691 82.0942) 
                         (list 210.722 81.9586) 
                         (list 210.734 81.9031) 
                         (list 210.752 81.1137) 
                         (list 210.74 81.0396) 
                         (list 210.715 80.8608) 
                         (list 210.685 80.7005) 
                         (list 210.629 80.5031) 
                         (list 210.574 80.4044) 
                         (list 210.549 80.3304) 
                         (list 210.493 80.2749) 
                         (list 210.426 80.2379) 
                         (list 210.345 80.1947) 
                         (list 210.228 80.1639) 
                         (list 210.056 80.1454) 
                         (list 209.865 80.1454) 
                         (list 208.804 80.1454) 
                         (list 208.749 80.1269) 
                         (list 208.743 80.0961) 
                         (list 208.749 79.7569) 
                         (list 208.7 79.7445) 
                         "c"
         )
        (command "pline" (list 210.648 95.8612) "w" 0 0 
                         (list 210.641 96.8726) 
                         (list 209.365 98.4391) 
                         (list 210.444 98.069) 
                         (list 210.629 97.9333) 
                         (list 210.648 98.8708) 
                         (list 208.472 99.543) 
                         (list 208.484 98.5932) 
                         (list 210.567 95.9845) 
                         (list 210.617 95.8612) 
                         "c"
         )
        (command "pline" (list 210.013 99.8037) "w" 0 0 
                         (list 210.074 99.7667) 
                         (list 210.611 99.7729) 
                         (list 210.648 99.8346) 
                         (list 210.648 100.02) 
                         (list 210.598 100.094) 
                         (list 210.543 100.205) 
                         (list 210.586 100.291) 
                         (list 210.635 100.482) 
                         (list 210.672 100.71) 
                         (list 210.678 100.982) 
                         (list 210.672 101.259) 
                         (list 210.629 101.469) 
                         (list 210.512 101.728) 
                         (list 210.352 101.925) 
                         (list 210.272 102.005) 
                         (list 210.136 102.055) 
                         (list 209.969 102.086) 
                         (list 209.785 102.079) 
                         (list 209.63 101.999) 
                         (list 209.538 101.95) 
                         (list 209.47 101.851) 
                         (list 209.396 101.716) 
                         (list 209.335 101.537) 
                         (list 209.279 101.346) 
                         (list 209.236 101.161) 
                         (list 209.211 101.006) 
                         (list 209.18 100.84) 
                         (list 209.15 100.704) 
                         (list 209.125 100.531) 
                         (list 209.082 100.414) 
                         (list 209.057 100.291) 
                         (list 209.026 100.235) 
                         (list 208.971 100.192) 
                         (list 208.909 100.192) 
                         (list 208.86 100.198) 
                         (list 208.798 100.223) 
                         (list 208.743 100.297) 
                         (list 208.693 100.396) 
                         (list 208.669 100.476) 
                         (list 208.656 100.556) 
                         (list 208.626 100.649) 
                         (list 208.626 100.797) 
                         (list 208.626 100.945) 
                         (list 208.65 101.124) 
                         (list 208.712 101.272) 
                         (list 208.755 101.395) 
                         (list 208.891 101.5) 
                         (list 209.008 101.58) 
                         (list 209.082 101.635) 
                         (list 209.106 101.691) 
                         (list 209.106 101.82) 
                         (list 209.069 101.833) 
                         (list 208.539 101.833) 
                         (list 208.515 101.783) 
                         (list 208.527 101.623) 
                         (list 208.582 101.574) 
                         (list 208.601 101.518) 
                         (list 208.601 101.475) 
                         (list 208.601 101.413) 
                         (list 208.564 101.333) 
                         (list 208.509 101.136) 
                         (list 208.49 100.938) 
                         (list 208.484 100.766) 
                         (list 208.49 100.599) 
                         (list 208.521 100.42) 
                         (list 208.595 100.248) 
                         (list 208.656 100.1) 
                         (list 208.737 100.02) 
                         (list 208.835 99.9147) 
                         (list 208.952 99.8407) 
                         (list 209.125 99.7852) 
                         (list 209.273 99.8037) 
                         (list 209.433 99.8407) 
                         (list 209.526 99.9271) 
                         (list 209.581 100.013) 
                         (list 209.661 100.18) 
                         (list 209.741 100.414) 
                         (list 209.791 100.612) 
                         (list 209.809 100.772) 
                         (list 209.815 100.908) 
                         (list 209.84 101.074) 
                         (list 209.871 101.247) 
                         (list 209.92 101.432) 
                         (list 209.988 101.543) 
                         (list 210.074 101.623) 
                         (list 210.154 101.666) 
                         (list 210.278 101.66) 
                         (list 210.401 101.574) 
                         (list 210.45 101.469) 
                         (list 210.512 101.352) 
                         (list 210.537 101.241) 
                         (list 210.543 101.124) 
                         (list 210.561 100.982) 
                         (list 210.555 100.821) 
                         (list 210.53 100.686) 
                         (list 210.487 100.47) 
                         (list 210.407 100.346) 
                         (list 210.327 100.229) 
                         (list 210.222 100.124) 
                         (list 210.105 100.038) 
                         (list 210.037 100.001) 
                         "c"
         )
        (command "pline" (list 208.496 104.053) "w" 0 0 
                         (list 208.49 105.28) 
                         (list 208.607 105.286) 
                         (list 208.632 104.953) 
                         (list 208.65 104.774) 
                         (list 209.23 103.923) 
                         (list 210.45 105.194) 
                         (list 210.475 105.305) 
                         (list 210.475 105.638) 
                         (list 210.592 105.656) 
                         (list 210.611 103.899) 
                         (list 210.469 103.886) 
                         (list 210.463 104.195) 
                         (list 209.581 103.264) 
                         (list 209.606 103.257) 
                         (list 209.63 103.239) 
                         (list 210.45 103.257) 
                         (list 210.487 103.294) 
                         (list 210.487 103.646) 
                         (list 210.58 103.658) 
                         (list 210.604 103.627) 
                         (list 210.617 102.005) 
                         (list 210.574 101.993) 
                         (list 210.5 101.993) 
                         (list 210.487 102.049) 
                         (list 210.469 102.382) 
                         (list 208.656 102.363) 
                         (list 208.65 102.079) 
                         (list 208.644 101.993) 
                         (list 208.533 101.981) 
                         (list 208.515 102.061) 
                         (list 208.502 103.634) 
                         (list 208.613 103.634) 
                         (list 208.644 103.609) 
                         (list 208.65 103.264) 
                         (list 208.706 103.239) 
                         (list 209.452 103.239) 
                         (list 209.476 103.27) 
                         (list 208.681 104.441) 
                         (list 208.626 104.417) 
                         (list 208.638 104.115) 
                         (list 208.619 104.034) 
                         (list 208.521 104.034) 
                         "c"
         )
  )
  (dg)
  (setq prd_id (getstring T "请输入产品ID:"))

  (command "style" "ht" "simhei.ttf" "" "" "" "" "" "")
  (command "s" "ht" "text" '(204 75) "3" "90" prd_id)
  (setq c_date (rtos (getvar "CDATE")))
  (setq	c_date (strcat (substr c_date 1 4)
		       "/"
		       (substr c_date 5 2)
		       "/"
		       (substr c_date 7 2)
	       )
  )
  (setq	txt_dt (list (cons 0 "TEXT")
		     (cons 1 c_date)
		     (cons 10 (list 210.8 107.4))
		     (cons 40 3)
		     (cons 50 (/ pi 2))
		     (cons 7 "ht")
	       )
  )
  (entmake txt_dt)

)
(prompt "\n输入'gw'运行")
