;运行程序，手工输入流程单号，程序会自动生成与流程单号相对应的3M边框!
(defun zero () 
        (command "pline" (list -266.804 2466.47) "w" 0 0 
                         (list 44.3028 2466.47) 
                         (list 1374.0 2466.47) 
                         (list 1374.0 -2466.47) 
                         (list -1374.0 -2466.47) 
                         (list -1374.0 2466.47) 
                         (list -409.979 2466.47) 
                         (list -266.814 2466.47) 
                         (list -266.814 1480.75) 
                         (list -409.979 1480.75) 
                         (list -445.314 1476.09) 
                         (list -478.237 1462.44) 
                         (list -506.498 1440.72) 
                         (list -960.78 985.692) 
                         (list -982.412 957.46) 
                         (list -996.01 924.594) 
                         (list -1000.65 889.331) 
                         (list -1000.65 -929.289) 
                         (list -996.01 -964.553) 
                         (list -982.412 -997.418) 
                         (list -960.78 -1025.65) 
                         (list -506.498 -1480.68) 
                         (list -478.237 -1502.4) 
                         (list -445.314 -1516.05) 
                         (list -409.979 -1520.71) 
                         (list 44.3028 -1520.71) 
                         (list 79.6025 -1516.06) 
                         (list 112.497 -1502.43) 
                         (list 140.743 -1480.76) 
                         (list 595.772 -1025.73) 
                         (list 617.446 -997.483) 
                         (list 631.072 -964.589) 
                         (list 635.719 -929.289) 
                         (list 635.719 889.331) 
                         (list 631.072 924.63) 
                         (list 617.446 957.524) 
                         (list 595.772 985.771) 
                         (list 140.743 1440.8) 
                         (list 112.497 1462.47) 
                         (list 79.6025 1476.1) 
                         (list 44.3028 1480.75) 
                         (list -266.804 1480.75) 
                         "c"
         )
        (command "pline" (list 362.944 832.837) "w" 0 0 
                         (list 362.944 -872.796) 
                         (list -12.1907 -1247.93) 
                         (list -353.419 -1247.93) 
                         (list -727.873 -872.861) 
                         (list -727.873 832.903) 
                         (list -353.419 1207.97) 
                         (list -12.1907 1207.97) 
                         "c"
         )
  )
(defun one () 
        (command "pline" (list -538.901 -1520.71) "w" 0 0 
                         (list 60.7103 -1520.71) 
                         (list 96.0099 -1516.06) 
                         (list 128.904 -1502.43) 
                         (list 157.151 -1480.76) 
                         (list 178.825 -1452.51) 
                         (list 192.45 -1419.62) 
                         (list 197.098 -1384.32) 
                         (list 192.45 -1349.02) 
                         (list 178.825 -1316.12) 
                         (list 157.151 -1287.88) 
                         (list 128.904 -1266.2) 
                         (list 96.0099 -1252.58) 
                         (list 60.7103 -1247.93) 
                         (list -257.184 -1247.93) 
                         (list -257.184 1344.36) 
                         (list -261.831 1379.66) 
                         (list -275.456 1412.55) 
                         (list -297.131 1440.8) 
                         (list -325.377 1462.47) 
                         (list -358.271 1476.1) 
                         (list -393.571 1480.75) 
                         (list -428.871 1476.1) 
                         (list -461.765 1462.47) 
                         (list -490.012 1440.8) 
                         (list -945.04 985.771) 
                         (list -966.715 957.524) 
                         (list -980.34 924.63) 
                         (list -984.987 889.331) 
                         (list -980.34 854.031) 
                         (list -966.715 821.137) 
                         (list -945.04 792.89) 
                         (list -916.793 771.216) 
                         (list -883.899 757.591) 
                         (list -848.6 752.943) 
                         (list -813.3 757.591) 
                         (list -780.406 771.216) 
                         (list -752.159 792.89) 
                         (list -529.958 1015.09) 
                         (list -529.958 -1247.93) 
                         (list -848.6 -1247.93) 
                         (list -883.899 -1252.58) 
                         (list -916.793 -1266.2) 
                         (list -945.04 -1287.88) 
                         (list -966.715 -1316.12) 
                         (list -980.34 -1349.02) 
                         (list -984.987 -1384.32) 
                         (list -980.34 -1419.62) 
                         (list -966.715 -1452.51) 
                         (list -945.04 -1480.76) 
                         (list -916.793 -1502.43) 
                         (list -883.899 -1516.06) 
                         (list -848.6 -1520.71) 
                         (list -538.911 -1520.71) 
                         (list -538.911 -2466.47) 
                         (list -1374.0 -2466.47) 
                         (list -1374.0 2466.47) 
                         (list -393.571 2466.47) 
                         (list 1374.0 2466.47) 
                         (list 1374.0 -2466.47) 
                         (list -538.901 -2466.47) 
                         "c"
         )
  )
(defun two () 
        (command "pline" (list 27.6798 2466.47) "w" 0 0 
                         (list 631.765 2466.47) 
                         (list 1374.0 2466.47) 
                         (list 1374.0 -2466.47) 
                         (list -1374.0 -2466.47) 
                         (list -1374.0 2466.47) 
                         (list 27.6698 2466.47) 
                         (list 27.6698 1455.21) 
                         (list -276.798 1455.21) 
                         (list -312.133 1450.55) 
                         (list -345.056 1436.9) 
                         (list -373.317 1415.19) 
                         (list -827.599 960.157) 
                         (list -849.25 931.892) 
                         (list -862.848 898.987) 
                         (list -867.466 863.684) 
                         (list -862.79 828.388) 
                         (list -849.138 795.505) 
                         (list -827.44 767.276) 
                         (list -799.176 745.625) 
                         (list -766.27 732.027) 
                         (list -730.967 727.408) 
                         (list -695.671 732.085) 
                         (list -662.788 745.737) 
                         (list -634.559 767.435) 
                         (list -220.238 1182.44) 
                         (list 575.206 1182.44) 
                         (list 949.659 807.368) 
                         (list 949.659 465.942) 
                         (list 575.206 90.8731) 
                         (list -276.798 90.8731) 
                         (list -312.133 86.2162) 
                         (list -345.056 72.5633) 
                         (list -373.317 50.8469) 
                         (list -827.599 -404.182) 
                         (list -849.231 -432.414) 
                         (list -862.829 -465.279) 
                         (list -867.466 -500.543) 
                         (list -867.466 -1409.85) 
                         (list -862.819 -1445.15) 
                         (list -849.194 -1478.05) 
                         (list -827.519 -1506.29) 
                         (list -799.273 -1527.97) 
                         (list -766.379 -1541.59) 
                         (list -731.079 -1546.24) 
                         (list 1086.05 -1546.24) 
                         (list 1121.35 -1541.59) 
                         (list 1154.24 -1527.97) 
                         (list 1182.49 -1506.29) 
                         (list 1204.16 -1478.05) 
                         (list 1217.79 -1445.15) 
                         (list 1222.43 -1409.85) 
                         (list 1217.79 -1374.55) 
                         (list 1204.16 -1341.66) 
                         (list 1182.49 -1313.41) 
                         (list 1154.24 -1291.74) 
                         (list 1121.35 -1278.11) 
                         (list 1086.05 -1273.47) 
                         (list -594.692 -1273.47) 
                         (list -594.692 -556.971) 
                         (list -220.238 -181.902) 
                         (list 631.765 -181.902) 
                         (list 667.101 -177.245) 
                         (list 700.024 -163.592) 
                         (list 728.285 -141.875) 
                         (list 1182.57 313.153) 
                         (list 1204.2 341.385) 
                         (list 1217.8 374.251) 
                         (list 1222.43 409.514) 
                         (list 1222.43 863.796) 
                         (list 1217.8 899.059) 
                         (list 1204.2 931.925) 
                         (list 1182.57 960.157) 
                         (list 728.285 1415.19) 
                         (list 700.024 1436.9) 
                         (list 667.101 1450.55) 
                         (list 631.765 1455.21) 
                         (list 27.6798 1455.21) 
                         "c"
         )
  )
(defun three () 
        (command "pline" (list 45.5618 2466.47) "w" 0 0 
                         (list 631.765 2466.47) 
                         (list 654.359 2466.47) 
                         (list 1374.0 2466.47) 
                         (list 1374.0 -2466.47) 
                         (list -1374.0 -2466.47) 
                         (list -1374.0 2466.47) 
                         (list -242.797 2466.47) 
                         (list 45.5518 2466.47) 
                         (list 45.5518 1466.94) 
                         (list -242.789 1466.94) 
                         (list -282.719 1461.68) 
                         (list -319.918 1446.27) 
                         (list -351.858 1421.75) 
                         (list -800.432 972.921) 
                         (list -823.35 943.652) 
                         (list -838.597 909.749) 
                         (list -845.288 873.183) 
                         (list -843.034 836.078) 
                         (list -831.965 800.59) 
                         (list -812.725 768.783) 
                         (list -786.432 742.504) 
                         (list -754.615 723.281) 
                         (list -719.121 712.231) 
                         (list -682.015 709.997) 
                         (list -645.452 716.707) 
                         (list -611.557 731.973) 
                         (list -582.301 754.907) 
                         (list -178.895 1158.54) 
                         (list 590.464 1158.54) 
                         (list 948.733 800.069) 
                         (list 948.733 478.679) 
                         (list 590.464 120.207) 
                         (list 205.785 120.207) 
                         (list 168.882 115.726) 
                         (list 134.124 102.544) 
                         (list 103.531 81.4275) 
                         (list 78.8805 53.6027) 
                         (list 61.6051 20.6872) 
                         (list 52.7089 -15.4061) 
                         (list 52.7089 -52.5796) 
                         (list 61.6051 -88.6729) 
                         (list 78.8805 -121.588) 
                         (list 103.531 -149.413) 
                         (list 134.124 -170.53) 
                         (list 168.882 -183.712) 
                         (list 205.785 -188.193) 
                         (list 590.464 -188.193) 
                         (list 948.733 -546.665) 
                         (list 948.733 -868.048) 
                         (list 590.464 -1226.53) 
                         (list -178.895 -1226.53) 
                         (list -582.301 -822.892) 
                         (list -611.556 -799.959) 
                         (list -645.45 -784.693) 
                         (list -682.013 -777.982) 
                         (list -719.119 -780.216) 
                         (list -754.612 -791.265) 
                         (list -786.429 -810.487) 
                         (list -812.722 -836.765) 
                         (list -831.962 -868.572) 
                         (list -843.031 -904.058) 
                         (list -845.286 -941.163) 
                         (list -838.596 -977.729) 
                         (list -823.349 -1011.63) 
                         (list -800.432 -1040.9) 
                         (list -351.858 -1489.73) 
                         (list -319.917 -1514.25) 
                         (list -282.715 -1529.67) 
                         (list -242.789 -1534.93) 
                         (list 654.359 -1534.93) 
                         (list 694.284 -1529.67) 
                         (list 731.486 -1514.25) 
                         (list 763.427 -1489.73) 
                         (list 1212.0 -1040.9) 
                         (list 1236.49 -1008.97) 
                         (list 1251.88 -971.793) 
                         (list 1257.13 -931.899) 
                         (list 1257.13 -482.82) 
                         (list 1251.88 -442.924) 
                         (list 1236.49 -405.745) 
                         (list 1212.0 -373.813) 
                         (list 872.367 -33.9928) 
                         (list 1212.0 305.827) 
                         (list 1236.49 337.759) 
                         (list 1251.88 374.938) 
                         (list 1257.13 414.834) 
                         (list 1257.13 863.914) 
                         (list 1251.88 903.809) 
                         (list 1236.49 940.989) 
                         (list 1212.0 972.921) 
                         (list 763.427 1421.75) 
                         (list 731.485 1446.27) 
                         (list 694.283 1461.68) 
                         (list 654.359 1466.94) 
                         (list 45.5618 1466.94) 
                         "c"
         )
  )
(defun four () 
        (command "pline" (list -408.672 -2466.47) "w" 0 0 
                         (list -1374.0 -2466.47) 
                         (list -1374.0 2466.47) 
                         (list -704.949 2466.47) 
                         (list 436.77 2466.47) 
                         (list 539.654 2466.47) 
                         (list 1374.0 2466.47) 
                         (list 1374.0 -2466.47) 
                         (list -408.662 -2466.47) 
                         (list -408.662 -633.361) 
                         (list 385.453 -633.361) 
                         (list 385.453 -1377.07) 
                         (list 389.934 -1413.97) 
                         (list 403.115 -1448.73) 
                         (list 424.232 -1479.32) 
                         (list 452.057 -1503.97) 
                         (list 484.973 -1521.25) 
                         (list 521.066 -1530.14) 
                         (list 558.239 -1530.14) 
                         (list 594.333 -1521.25) 
                         (list 627.248 -1503.97) 
                         (list 655.073 -1479.32) 
                         (list 676.19 -1448.73) 
                         (list 689.372 -1413.97) 
                         (list 693.853 -1377.07) 
                         (list 693.853 -633.361) 
                         (list 988.227 -633.361) 
                         (list 1025.13 -628.88) 
                         (list 1059.89 -615.699) 
                         (list 1090.48 -594.582) 
                         (list 1115.13 -566.757) 
                         (list 1132.41 -533.841) 
                         (list 1141.3 -497.748) 
                         (list 1141.3 -460.575) 
                         (list 1132.41 -424.481) 
                         (list 1115.13 -391.566) 
                         (list 1090.48 -363.741) 
                         (list 1059.89 -342.624) 
                         (list 1025.13 -329.442) 
                         (list 988.227 -324.961) 
                         (list 693.853 -324.961) 
                         (list 693.853 1316.4) 
                         (list 688.599 1356.31) 
                         (list 673.195 1393.5) 
                         (list 648.69 1425.44) 
                         (list 616.754 1449.94) 
                         (list 579.564 1465.35) 
                         (list 539.654 1470.6) 
                         (list 504.213 1466.47) 
                         (list 470.67 1454.31) 
                         (list 440.82 1434.76) 
                         (list 416.262 1408.88) 
                         (list -929.466 -386.684) 
                         (list -948.271 -419.518) 
                         (list -958.513 -455.942) 
                         (list -959.578 -493.763) 
                         (list -951.4 -530.706) 
                         (list -934.473 -564.545) 
                         (list -909.815 -593.243) 
                         (list -878.91 -615.072) 
                         (list -843.62 -628.719) 
                         (list -806.069 -633.361) 
                         (list -408.672 -633.361) 
                         "c"
         )
        (command "pline" (list 385.453 853.54) "w" 0 0 
                         (list -497.799 -324.961) 
                         (list 385.453 -324.961) 
                         "c"
         )
  )
(defun five () 
        (command "pline" (list 17.8963 2466.47) "w" 0 0 
                         (list 436.77 2466.47) 
                         (list 1374.0 2466.47) 
                         (list 1374.0 -2466.47) 
                         (list -1374.0 -2466.47) 
                         (list -1374.0 2466.47) 
                         (list -704.949 2466.47) 
                         (list 17.8863 2466.47) 
                         (list 17.8863 1500.99) 
                         (list -704.949 1500.99) 
                         (list -744.859 1495.74) 
                         (list -782.048 1480.33) 
                         (list -813.984 1455.83) 
                         (list -838.489 1423.89) 
                         (list -853.894 1386.7) 
                         (list -859.149 1346.79) 
                         (list -859.149 448.884) 
                         (list -853.894 408.974) 
                         (list -838.489 371.785) 
                         (list -813.984 339.849) 
                         (list -782.048 315.344) 
                         (list -744.859 299.939) 
                         (list -704.949 294.684) 
                         (list 576.878 294.684) 
                         (list 935.147 -63.7879) 
                         (list 935.147 -833.998) 
                         (list 576.878 -1192.48) 
                         (list -192.481 -1192.48) 
                         (list -595.887 -788.842) 
                         (list -625.142 -765.909) 
                         (list -659.036 -750.643) 
                         (list -695.598 -743.932) 
                         (list -732.704 -746.166) 
                         (list -768.198 -757.215) 
                         (list -800.015 -776.437) 
                         (list -826.308 -802.715) 
                         (list -845.548 -834.522) 
                         (list -856.617 -870.008) 
                         (list -858.872 -907.113) 
                         (list -852.182 -943.679) 
                         (list -836.935 -977.582) 
                         (list -814.018 -1006.85) 
                         (list -365.444 -1455.68) 
                         (list -333.502 -1480.2) 
                         (list -296.3 -1495.62) 
                         (list -256.375 -1500.88) 
                         (list 640.773 -1500.88) 
                         (list 680.698 -1495.62) 
                         (list 717.9 -1480.2) 
                         (list 749.841 -1455.68) 
                         (list 1198.42 -1006.85) 
                         (list 1222.9 -974.92) 
                         (list 1238.29 -937.743) 
                         (list 1243.55 -897.85) 
                         (list 1243.55 0.0570701) 
                         (list 1238.3 39.9528) 
                         (list 1222.9 77.1321) 
                         (list 1198.42 109.064) 
                         (list 749.841 557.891) 
                         (list 717.899 582.413) 
                         (list 680.697 597.827) 
                         (list 640.773 603.084) 
                         (list -550.749 603.084) 
                         (list -550.749 1192.59) 
                         (list 1089.35 1192.59) 
                         (list 1126.25 1197.07) 
                         (list 1161.01 1210.25) 
                         (list 1191.6 1231.37) 
                         (list 1216.25 1259.19) 
                         (list 1233.53 1292.11) 
                         (list 1242.42 1328.2) 
                         (list 1242.42 1365.38) 
                         (list 1233.53 1401.47) 
                         (list 1216.25 1434.39) 
                         (list 1191.6 1462.21) 
                         (list 1161.01 1483.33) 
                         (list 1126.25 1496.51) 
                         (list 1089.35 1500.99) 
                         (list 17.8963 1500.99) 
                         "c"
         )
  )
(defun six () 
        (command "pline" (list 26.3687 -1522.27) "w" 0 0 
                         (list 720.721 -1522.27) 
                         (list 760.646 -1517.01) 
                         (list 797.848 -1501.6) 
                         (list 829.79 -1477.07) 
                         (list 1278.36 -1028.25) 
                         (list 1302.85 -996.316) 
                         (list 1318.24 -959.139) 
                         (list 1323.49 -919.245) 
                         (list 1323.49 -470.166) 
                         (list 1318.24 -430.27) 
                         (list 1302.85 -393.091) 
                         (list 1278.36 -361.159) 
                         (list 829.79 87.6682) 
                         (list 797.847 112.19) 
                         (list 760.645 127.605) 
                         (list 720.721 132.861) 
                         (list -470.801 132.861) 
                         (list -470.801 363.655) 
                         (list 336.053 1171.19) 
                         (list 720.721 1171.19) 
                         (list 757.623 1175.68) 
                         (list 792.381 1188.86) 
                         (list 822.974 1209.97) 
                         (list 847.625 1237.8) 
                         (list 864.9 1270.71) 
                         (list 873.796 1306.81) 
                         (list 873.796 1343.98) 
                         (list 864.9 1380.07) 
                         (list 847.625 1412.99) 
                         (list 822.974 1440.81) 
                         (list 792.381 1461.93) 
                         (list 757.623 1475.11) 
                         (list 720.721 1479.59) 
                         (list 272.147 1479.59) 
                         (list 232.216 1474.33) 
                         (list 195.01 1458.91) 
                         (list 163.066 1434.38) 
                         (list -734.088 536.477) 
                         (list -758.567 504.549) 
                         (list -773.954 467.376) 
                         (list -779.201 427.488) 
                         (list -779.201 -919.245) 
                         (list -773.949 -959.139) 
                         (list -758.556 -996.316) 
                         (list -734.07 -1028.25) 
                         (list -285.496 -1477.07) 
                         (list -253.554 -1501.6) 
                         (list -216.352 -1517.01) 
                         (list -176.427 -1522.27) 
                         (list 26.3587 -1522.27) 
                         (list 26.3587 -2466.47) 
                         (list -1374.0 -2466.47) 
                         (list -1374.0 2466.47) 
                         (list -704.949 2466.47) 
                         (list 272.147 2466.47) 
                         (list 436.77 2466.47) 
                         (list 1374.0 2466.47) 
                         (list 1374.0 -2466.47) 
                         (list 26.3687 -2466.47) 
                         "c"
         )
        (command "pline" (list -470.801 -855.394) "w" 0 0 
                         (list -112.533 -1213.87) 
                         (list 656.826 -1213.87) 
                         (list 1015.09 -855.394) 
                         (list 1015.09 -534.011) 
                         (list 656.826 -175.539) 
                         (list -470.801 -175.539) 
                         "c"
         )
  )
(defun seven () 
        (command "pline" (list 101.938 2466.47) "w" 0 0 
                         (list 436.77 2466.47) 
                         (list 1151.04 2466.47) 
                         (list 1374.0 2466.47) 
                         (list 1374.0 -2466.47) 
                         (list -1374.0 -2466.47) 
                         (list -1374.0 2466.47) 
                         (list -704.949 2466.47) 
                         (list -643.258 2466.47) 
                         (list 101.928 2466.47) 
                         (list 101.928 1460.51) 
                         (list -643.258 1460.51) 
                         (list -680.161 1456.03) 
                         (list -714.919 1442.85) 
                         (list -745.512 1421.73) 
                         (list -770.162 1393.91) 
                         (list -787.438 1360.99) 
                         (list -796.334 1324.9) 
                         (list -796.334 1287.72) 
                         (list -787.438 1251.63) 
                         (list -770.162 1218.72) 
                         (list -745.512 1190.89) 
                         (list -714.919 1169.77) 
                         (list -680.161 1156.59) 
                         (list -643.258 1152.11) 
                         (list 901.622 1152.11) 
                         (list -332.625 -1318.23) 
                         (list -345.11 -1353.25) 
                         (list -348.853 -1390.23) 
                         (list -343.636 -1427.04) 
                         (list -329.762 -1461.53) 
                         (list -308.039 -1491.69) 
                         (list -279.727 -1515.78) 
                         (list -246.473 -1532.39) 
                         (list -210.209 -1540.57) 
                         (list -173.043 -1539.83) 
                         (list -137.135 -1530.21) 
                         (list -104.571 -1512.28) 
                         (list -77.2447 -1487.08) 
                         (list -56.7432 -1456.07) 
                         (list 1288.98 1237.39) 
                         (list 1301.88 1274.3) 
                         (list 1305.08 1313.27) 
                         (list 1298.37 1351.8) 
                         (list 1282.19 1387.4) 
                         (list 1257.58 1417.78) 
                         (list 1226.12 1441.0) 
                         (list 1189.82 1455.55) 
                         (list 1151.04 1460.51) 
                         (list 101.938 1460.51) 
                         "c"
         )
  )
(defun eight () 
        (command "pline" (list 392.798 202.5) "w" 0 0 
                         (list 751.066 560.972) 
                         (list 751.066 882.362) 
                         (list 392.798 1240.83) 
                         (list -376.561 1240.83) 
                         (list -734.83 882.362) 
                         (list -734.83 560.972) 
                         (list -376.561 202.5) 
                         "c"
         )
        (command "pline" (list -376.561 -105.9) "w" 0 0 
                         (list -734.83 -464.371) 
                         (list -734.83 -785.755) 
                         (list -376.561 -1144.23) 
                         (list 392.798 -1144.23) 
                         (list 751.066 -785.755) 
                         (list 751.066 -464.371) 
                         (list 392.798 -105.9) 
                         "c"
         )
        (command "pline" (list -480.385 1543.98) "w" 0 0 
                         (list -517.584 1528.56) 
                         (list -549.524 1504.04) 
                         (list -998.098 1055.21) 
                         (list -1022.58 1023.28) 
                         (list -1037.98 986.103) 
                         (list -1043.23 946.207) 
                         (list -1043.23 497.127) 
                         (list -1037.98 457.232) 
                         (list -1022.58 420.052) 
                         (list -998.098 388.12) 
                         (list -658.47 48.3004) 
                         (list -998.098 -291.519) 
                         (list -1022.58 -323.451) 
                         (list -1037.98 -360.631) 
                         (list -1043.23 -400.526) 
                         (list -1043.23 -849.606) 
                         (list -1037.98 -889.5) 
                         (list -1022.58 -926.677) 
                         (list -998.098 -958.607) 
                         (list -549.524 -1407.43) 
                         (list -517.583 -1431.96) 
                         (list -480.381 -1447.37) 
                         (list -440.456 -1452.63) 
                         (list 456.692 -1452.63) 
                         (list 496.618 -1447.37) 
                         (list 533.82 -1431.96) 
                         (list 565.761 -1407.43) 
                         (list 1014.34 -958.607) 
                         (list 1038.82 -926.677) 
                         (list 1054.21 -889.5) 
                         (list 1059.47 -849.606) 
                         (list 1059.47 -400.526) 
                         (list 1054.21 -360.631) 
                         (list 1038.82 -323.451) 
                         (list 1014.34 -291.519) 
                         (list 674.7 48.3004) 
                         (list 1014.34 388.12) 
                         (list 1038.82 420.052) 
                         (list 1054.21 457.232) 
                         (list 1059.47 497.127) 
                         (list 1059.47 946.207) 
                         (list 1054.21 986.103) 
                         (list 1038.82 1023.28) 
                         (list 1014.34 1055.21) 
                         (list 565.761 1504.04) 
                         (list 533.819 1528.56) 
                         (list 496.617 1543.98) 
                         (list 456.692 1549.23) 
                         (list -96.8628 1549.23) 
                         (list -96.8628 2466.47) 
                         (list 436.77 2466.47) 
                         (list 456.692 2466.47) 
                         (list 1374.0 2466.47) 
                         (list 1374.0 -2466.47) 
                         (list -1374.0 -2466.47) 
                         (list -1374.0 2466.47) 
                         (list -704.949 2466.47) 
                         (list -172.616 2466.47) 
                         (list -96.8728 2466.47) 
                         (list -96.8728 1549.23) 
                         (list -440.456 1549.23) 
                         "c"
         )
  )
(defun nine () 
        (command "pline" (list -143.815 2466.47) "w" 0 0 
                         (list 436.77 2466.47) 
                         (list 1374.0 2466.47) 
                         (list 1374.0 -2466.47) 
                         (list -1374.0 -2466.47) 
                         (list -1374.0 2466.47) 
                         (list -143.825 2466.47) 
                         (list -143.825 1482.31) 
                         (list -471.793 1482.31) 
                         (list -507.129 1477.66) 
                         (list -540.052 1464.0) 
                         (list -568.313 1442.29) 
                         (list -1022.59 987.26) 
                         (list -1044.23 959.028) 
                         (list -1057.82 926.162) 
                         (list -1062.46 890.899) 
                         (list -1062.46 436.617) 
                         (list -1057.82 401.354) 
                         (list -1044.23 368.488) 
                         (list -1022.59 340.256) 
                         (list -568.313 -114.773) 
                         (list -540.052 -136.489) 
                         (list -507.129 -150.142) 
                         (list -471.793 -154.799) 
                         (list 754.664 -154.799) 
                         (list 754.664 -416.979) 
                         (list -74.0382 -1246.36) 
                         (list -471.793 -1246.36) 
                         (list -507.093 -1251.01) 
                         (list -539.987 -1264.64) 
                         (list -568.234 -1286.31) 
                         (list -589.908 -1314.56) 
                         (list -603.533 -1347.45) 
                         (list -608.181 -1382.75) 
                         (list -603.533 -1418.05) 
                         (list -589.908 -1450.94) 
                         (list -568.234 -1479.19) 
                         (list -539.987 -1500.86) 
                         (list -507.093 -1514.49) 
                         (list -471.793 -1519.14) 
                         (list -17.5118 -1519.14) 
                         (list 17.8059 -1514.49) 
                         (list 50.7142 -1500.85) 
                         (list 78.9682 -1479.15) 
                         (list 987.531 -569.841) 
                         (list 1009.18 -541.601) 
                         (list 1022.8 -508.722) 
                         (list 1027.44 -473.44) 
                         (list 1027.44 890.899) 
                         (list 1022.8 926.162) 
                         (list 1009.2 959.028) 
                         (list 987.571 987.26) 
                         (list 533.289 1442.29) 
                         (list 505.028 1464.0) 
                         (list 472.105 1477.66) 
                         (list 436.77 1482.31) 
                         (list -143.815 1482.31) 
                         "c"
         )
        (command "pline" (list -415.234 1209.54) "w" 0 0 
                         (list 380.21 1209.54) 
                         (list 754.664 834.471) 
                         (list 754.664 117.976) 
                         (list -415.234 117.976) 
                         (list -789.687 493.045) 
                         (list -789.687 834.471) 
                         "c"
         )
  )

(defun scale (layer_name ke kf)
    (setq ke 0.76)
    (setq kf 0.793304)
    
    (setq
      ss_lwpl (ssget "x"
		     (list (cons 0 "lwpolyline") (cons 8 layer_name))
	      )
    )
    (if	ss_lwpl
      (progn
	(setq ss_cnt (sslength ss_lwpl))
	(setq i_loop 0)
	(while (< i_loop ss_cnt)
	  (setq pl_dt (entget (ssname ss_lwpl i_loop)))
	  (setq dt nil)
	  (while pl_dt
	    (if	(/= (caar pl_dt) 10)
	      (setq dt (append dt (list (car pl_dt))))
	      (progn
		(setq scl_x (*(cadar pl_dt) kf))
		(setq scl_y (* (caddar pl_dt) ke))
		(setq
		  dt (append dt (list (cons 10 (list scl_x scl_y 0))))
		)
	      )
	    )
	    (setq pl_dt (cdr pl_dt))
	  )
	  (entmod dt)
	  (setq i_loop (1+ i_loop))
        )
     ) 
    )
   
    
);        defun scale(layer_name ke)
(defun draw_edge1 () 
        
        
        (command "pline" (list 124209.0 -171155.0) "w" 0 0 
                         (list 124209.0 -171397.0) 
                         (list 124210.0 -171397.0) 
                         (list 124210.0 -171435.0) 
                         (list 104292.0 -171435.0) 
                         (list 104292.0 -171397.0) 
                         (list 124209.0 -171397.0) 
                         (list 124209.0 -171155.0) 
                         (list 124138.0 -171155.0) 
                         (list 124128.0 -171155.0) 
                         (list 124128.0 -171322.0) 
                         (list 124138.0 -171322.0) 
                         (list 124138.0 -171360.0) 
                         (list 104292.0 -171360.0) 
                         (list 104292.0 -171322.0) 
                         (list 124128.0 -171322.0) 
                         (list 124128.0 -171155.0) 
                         (list 103559.0 -171155.0) 
                         (list 103559.0 -172353.0) 
                         (list 125715.0 -172353.0) 
                         (list 125715.0 -171155.0) 
                         (list 124292.0 -171155.0) 
                         (list 124292.0 -171472.0) 
                         (list 124292.0 -171510.0) 
                         (list 104292.0 -171510.0) 
                         (list 104292.0 -171472.0) 
                         (list 124292.0 -171472.0) 
                         (list 124292.0 -171155.0) 
                         (list 124210.0 -171155.0) 
                         "c"
         )
        (command "pline" (list 175050.0 175050.0) "w" 0 0 
                         (list 175150.0 175050.0) 
                         (list 175150.0 175150.0) 
                         (list 175050.0 175150.0) 
                         "c"
         )
        (command "pline" (list 175050.0 -175150.0) "w" 0 0 
                         (list 175150.0 -175150.0) 
                         (list 175150.0 -175050.0) 
                         (list 175050.0 -175050.0) 
                         "c"
         )
        (command "pline" (list -175150.0 -175150.0) "w" 0 0 
                         (list -175050.0 -175150.0) 
                         (list -175050.0 -175050.0) 
                         (list -175150.0 -175050.0) 
                         "c"
         )
        (command "pline" (list -175150.0 175050.0) "w" 0 0 
                         (list -175050.0 175050.0) 
                         (list -175050.0 175150.0) 
                         (list -175150.0 175150.0) 
                         "c"
         )
        (command "pline" (list 175050.0 175050.0) "w" 0 0 
                         (list 175150.0 175050.0) 
                         (list 175150.0 175150.0) 
                         (list 175050.0 175150.0) 
                         "c"
         )
        (command "pline" (list 175050.0 -175150.0) "w" 0 0 
                         (list 175150.0 -175150.0) 
                         (list 175150.0 -175050.0) 
                         (list 175050.0 -175050.0) 
                         "c"
         )
        (command "pline" (list -175150.0 -175150.0) "w" 0 0 
                         (list -175050.0 -175150.0) 
                         (list -175050.0 -175050.0) 
                         (list -175150.0 -175050.0) 
                         "c"
         )
        (command "pline" (list -175150.0 175050.0) "w" 0 0 
                         (list -175050.0 175050.0) 
                         (list -175050.0 175150.0) 
                         (list -175150.0 175150.0) 
                         "c"
         )
        (command "pline" (list -175000.0 -175000.0) "w" 0 0 
                         (list 88667.4 -175000.0) 
                         (list 88667.4 -165100.0) 
                         (list -175000.0 -165100.0) 
                         "c"
         )
        (command "pline" (list -175000.0 175000.0) "w" 0 0 
                         (list -175000.0 -165100.0) 
                         (list -165100.0 -165100.0) 
                         (list -165100.0 165100.0) 
                         (list 142700.0 165100.0) 
                         (list 165100.0 165100.0) 
                         (list 165100.0 -165100.0) 
                         (list 175000.0 -165100.0) 
                         (list 175000.0 175000.0) 
                         "c"
         )
        (command "pline" (list 175000.0 -165100.0) "w" 0 0 
                         (list 164216.0 -165100.0) 
                         (list 164216.0 -175000.0) 
                         (list 175000.0 -175000.0) 
                         "c"
         )
        (command "pline" (list 88667.4 -167420.0) "w" 0 0 
                         (list 96329.4 -167420.0) 
                         (list 96329.4 -172353.0) 
                         (list 88667.4 -172353.0) 
                         "c"
         )
        (command "pline" (list 125715.0 -167420.0) "w" 0 0 
                         (list 134568.0 -167420.0) 
                         (list 134568.0 -172353.0) 
                         (list 125715.0 -172353.0) 
                         "c"
         )
        (command "pline" (list 156671.0 -167420.0) "w" 0 0 
                         (list 164216.0 -167420.0) 
                         (list 164216.0 -172353.0) 
                         (list 156671.0 -172353.0) 
                         "c"
         )
        (command "pline" (list 88667.4 -175000.0) "w" 0 0 
                         (list 164216.0 -175000.0) 
                         (list 164216.0 -172353.0) 
                         (list 88667.4 -172353.0) 
                         "c"
         )
        (command "pline" (list 88667.4 -165100.0) "w" 0 0 
                         (list 164216.0 -165100.0) 
                         (list 164216.0 -167420.0) 
                         (list 88667.4 -167420.0) 
                         "c"
         )
        (command "pline" (list 125714.0 -167420.0) "w" 0 0 
                         (list 125715.0 -167420.0) 
                         (list 125715.0 -171155.0) 
                         (list 125714.0 -171155.0) 
                         "c"
         )
        (command "pline" (list 97404.0 -168437.0) "w" 0 0 
                         (list 96949.9 -168891.0) 
                         (list 96928.3 -168920.0) 
                         (list 96914.7 -168953.0) 
                         (list 96910.0 -168988.0) 
                         (list 96914.7 -169023.0) 
                         (list 96928.3 -169056.0) 
                         (list 96949.9 -169084.0) 
                         (list 98670.1 -170806.0) 
                         (list 98352.2 -171124.0) 
                         (list 97556.9 -171124.0) 
                         (list 97142.7 -170709.0) 
                         (list 97114.5 -170688.0) 
                         (list 97081.6 -170674.0) 
                         (list 97046.4 -170670.0) 
                         (list 97011.1 -170674.0) 
                         (list 96978.2 -170688.0) 
                         (list 96950.0 -170709.0) 
                         (list 96928.3 -170738.0) 
                         (list 96914.7 -170770.0) 
                         (list 96910.0 -170806.0) 
                         (list 96914.7 -170841.0) 
                         (list 96928.3 -170874.0) 
                         (list 96949.9 -170902.0) 
                         (list 97404.0 -171357.0) 
                         (list 97432.3 -171378.0) 
                         (list 97465.1 -171392.0) 
                         (list 97500.4 -171397.0) 
                         (list 98408.6 -171397.0) 
                         (list 98443.9 -171392.0) 
                         (list 98476.8 -171378.0) 
                         (list 98505.1 -171357.0) 
                         (list 98959.2 -170902.0) 
                         (list 98980.8 -170874.0) 
                         (list 98994.4 -170841.0) 
                         (list 98999.1 -170806.0) 
                         (list 98994.4 -170771.0) 
                         (list 98980.8 -170738.0) 
                         (list 98959.2 -170709.0) 
                         (list 97239.0 -168988.0) 
                         (list 97556.9 -168670.0) 
                         (list 98352.2 -168670.0) 
                         (list 98766.3 -169084.0) 
                         (list 98794.6 -169106.0) 
                         (list 98827.4 -169119.0) 
                         (list 98862.7 -169124.0) 
                         (list 98898.0 -169119.0) 
                         (list 98930.9 -169106.0) 
                         (list 98959.1 -169084.0) 
                         (list 98980.8 -169056.0) 
                         (list 98994.4 -169023.0) 
                         (list 98999.1 -168988.0) 
                         (list 98994.4 -168953.0) 
                         (list 98980.8 -168920.0) 
                         (list 98959.2 -168891.0) 
                         (list 98505.1 -168437.0) 
                         (list 98476.8 -168415.0) 
                         (list 98443.9 -168402.0) 
                         (list 98408.6 -168397.0) 
                         (list 97791.4 -168397.0) 
                         (list 97791.4 -167420.0) 
                         (list 98408.6 -167420.0) 
                         (list 99380.0 -167420.0) 
                         (list 99380.0 -172353.0) 
                         (list 96329.4 -172353.0) 
                         (list 96329.4 -167420.0) 
                         (list 97791.4 -167420.0) 
                         (list 97791.4 -168397.0) 
                         (list 97500.4 -168397.0) 
                         (list 97465.1 -168402.0) 
                         (list 97432.3 -168415.0) 
                         "c"
         )
        (command "pline" (list 99380.0 -170054.0) "w" 0 0 
                         (list 99380.0 -167420.0) 
                         (list 101587.0 -167420.0) 
                         (list 103559.0 -167420.0) 
                         (list 103559.0 -172353.0) 
                         (list 99380.0 -172353.0) 
                         (list 99380.0 -170054.0) 
                         (list 100141.0 -170054.0) 
                         (list 100141.0 -171260.0) 
                         (list 100146.0 -171296.0) 
                         (list 100159.0 -171328.0) 
                         (list 100181.0 -171357.0) 
                         (list 100209.0 -171378.0) 
                         (list 100242.0 -171392.0) 
                         (list 100277.0 -171397.0) 
                         (list 100312.0 -171392.0) 
                         (list 100345.0 -171378.0) 
                         (list 100374.0 -171357.0) 
                         (list 100395.0 -171328.0) 
                         (list 100409.0 -171296.0) 
                         (list 100414.0 -171260.0) 
                         (list 100414.0 -169111.0) 
                         (list 101063.0 -170412.0) 
                         (list 101082.0 -170440.0) 
                         (list 101107.0 -170463.0) 
                         (list 101136.0 -170478.0) 
                         (list 101168.0 -170486.0) 
                         (list 101202.0 -170486.0) 
                         (list 101234.0 -170478.0) 
                         (list 101264.0 -170463.0) 
                         (list 101289.0 -170440.0) 
                         (list 101307.0 -170412.0) 
                         (list 101957.0 -169111.0) 
                         (list 101957.0 -171260.0) 
                         (list 101962.0 -171296.0) 
                         (list 101975.0 -171328.0) 
                         (list 101997.0 -171357.0) 
                         (list 102025.0 -171378.0) 
                         (list 102058.0 -171392.0) 
                         (list 102093.0 -171397.0) 
                         (list 102129.0 -171392.0) 
                         (list 102162.0 -171378.0) 
                         (list 102190.0 -171357.0) 
                         (list 102211.0 -171328.0) 
                         (list 102225.0 -171296.0) 
                         (list 102230.0 -171260.0) 
                         (list 102230.0 -168533.0) 
                         (list 102225.0 -168498.0) 
                         (list 102211.0 -168465.0) 
                         (list 102190.0 -168437.0) 
                         (list 102162.0 -168415.0) 
                         (list 102129.0 -168402.0) 
                         (list 102093.0 -168397.0) 
                         (list 102056.0 -168402.0) 
                         (list 102022.0 -168417.0) 
                         (list 101993.0 -168441.0) 
                         (list 101971.0 -168472.0) 
                         (list 101185.0 -170046.0) 
                         (list 100399.0 -168472.0) 
                         (list 100381.0 -168445.0) 
                         (list 100356.0 -168422.0) 
                         (list 100327.0 -168407.0) 
                         (list 100295.0 -168398.0) 
                         (list 100262.0 -168398.0) 
                         (list 100230.0 -168405.0) 
                         (list 100201.0 -168421.0) 
                         (list 100176.0 -168442.0) 
                         (list 100157.0 -168470.0) 
                         (list 100145.0 -168501.0) 
                         (list 100141.0 -168533.0) 
                         (list 100141.0 -170054.0) 
                         "c"
         )
        (command "pline" (list 138640.0 -170700.0) "w" 0 0 
                         (list 138266.0 -171075.0) 
                         (list 137551.0 -171075.0) 
                         (list 137551.0 -168620.0) 
                         (list 138266.0 -168620.0) 
                         (list 138640.0 -168995.0) 
                         "c"
         )
        (command "pline" (list 135473.0 -167420.0) "w" 0 0 
                         (list 136052.0 -167420.0) 
                         (list 136488.0 -167420.0) 
                         (list 136488.0 -172353.0) 
                         (list 134568.0 -172353.0) 
                         (list 134568.0 -167420.0) 
                         (list 135473.0 -167420.0) 
                         (list 135473.0 -168348.0) 
                         (list 135144.0 -168348.0) 
                         (list 135108.0 -168352.0) 
                         (list 135076.0 -168366.0) 
                         (list 135047.0 -168388.0) 
                         (list 135026.0 -168416.0) 
                         (list 135012.0 -168449.0) 
                         (list 135007.0 -168484.0) 
                         (list 135012.0 -168519.0) 
                         (list 135026.0 -168552.0) 
                         (list 135047.0 -168580.0) 
                         (list 135076.0 -168602.0) 
                         (list 135108.0 -168616.0) 
                         (list 135144.0 -168620.0) 
                         (list 135461.0 -168620.0) 
                         (list 135461.0 -171075.0) 
                         (list 135144.0 -171075.0) 
                         (list 135108.0 -171080.0) 
                         (list 135076.0 -171093.0) 
                         (list 135047.0 -171115.0) 
                         (list 135026.0 -171143.0) 
                         (list 135012.0 -171176.0) 
                         (list 135007.0 -171211.0) 
                         (list 135012.0 -171247.0) 
                         (list 135026.0 -171280.0) 
                         (list 135047.0 -171308.0) 
                         (list 135076.0 -171329.0) 
                         (list 135108.0 -171343.0) 
                         (list 135144.0 -171348.0) 
                         (list 136052.0 -171348.0) 
                         (list 136088.0 -171343.0) 
                         (list 136120.0 -171329.0) 
                         (list 136149.0 -171308.0) 
                         (list 136170.0 -171280.0) 
                         (list 136184.0 -171247.0) 
                         (list 136189.0 -171211.0) 
                         (list 136184.0 -171176.0) 
                         (list 136170.0 -171143.0) 
                         (list 136149.0 -171115.0) 
                         (list 136120.0 -171093.0) 
                         (list 136088.0 -171080.0) 
                         (list 136052.0 -171075.0) 
                         (list 135734.0 -171075.0) 
                         (list 135734.0 -168620.0) 
                         (list 136052.0 -168620.0) 
                         (list 136088.0 -168616.0) 
                         (list 136120.0 -168602.0) 
                         (list 136149.0 -168580.0) 
                         (list 136170.0 -168552.0) 
                         (list 136184.0 -168519.0) 
                         (list 136189.0 -168484.0) 
                         (list 136184.0 -168449.0) 
                         (list 136170.0 -168416.0) 
                         (list 136149.0 -168388.0) 
                         (list 136120.0 -168366.0) 
                         (list 136088.0 -168352.0) 
                         (list 136052.0 -168348.0) 
                         (list 135473.0 -168348.0) 
                         "c"
         )
        (command "pline" (list 137551.0 -167420.0) "w" 0 0 
                         (list 138323.0 -167420.0) 
                         (list 139187.0 -167420.0) 
                         (list 139187.0 -172353.0) 
                         (list 136488.0 -172353.0) 
                         (list 136488.0 -167420.0) 
                         (list 137551.0 -167420.0) 
                         (list 137551.0 -168348.0) 
                         (list 136960.0 -168348.0) 
                         (list 136925.0 -168352.0) 
                         (list 136892.0 -168366.0) 
                         (list 136864.0 -168388.0) 
                         (list 136842.0 -168416.0) 
                         (list 136829.0 -168449.0) 
                         (list 136824.0 -168484.0) 
                         (list 136829.0 -168519.0) 
                         (list 136842.0 -168552.0) 
                         (list 136864.0 -168580.0) 
                         (list 136892.0 -168602.0) 
                         (list 136925.0 -168616.0) 
                         (list 136960.0 -168620.0) 
                         (list 137278.0 -168620.0) 
                         (list 137278.0 -171075.0) 
                         (list 136960.0 -171075.0) 
                         (list 136925.0 -171080.0) 
                         (list 136892.0 -171093.0) 
                         (list 136864.0 -171115.0) 
                         (list 136842.0 -171143.0) 
                         (list 136829.0 -171176.0) 
                         (list 136824.0 -171211.0) 
                         (list 136829.0 -171247.0) 
                         (list 136842.0 -171280.0) 
                         (list 136864.0 -171308.0) 
                         (list 136892.0 -171329.0) 
                         (list 136925.0 -171343.0) 
                         (list 136960.0 -171348.0) 
                         (list 138323.0 -171348.0) 
                         (list 138358.0 -171343.0) 
                         (list 138391.0 -171329.0) 
                         (list 138419.0 -171308.0) 
                         (list 138873.0 -170853.0) 
                         (list 138895.0 -170825.0) 
                         (list 138908.0 -170792.0) 
                         (list 138913.0 -170757.0) 
                         (list 138913.0 -168939.0) 
                         (list 138908.0 -168903.0) 
                         (list 138895.0 -168871.0) 
                         (list 138873.0 -168842.0) 
                         (list 138419.0 -168388.0) 
                         (list 138391.0 -168366.0) 
                         (list 138358.0 -168352.0) 
                         (list 138323.0 -168348.0) 
                         (list 137551.0 -168348.0) 
                         "c"
         )
        (command "pline" (list 139548.0 -169710.0) "w" 0 0 
                         (list 139548.0 -169848.0) 
                         (list 139553.0 -169883.0) 
                         (list 139567.0 -169916.0) 
                         (list 139588.0 -169944.0) 
                         (list 139617.0 -169966.0) 
                         (list 139649.0 -169979.0) 
                         (list 139685.0 -169984.0) 
                         (list 139720.0 -169979.0) 
                         (list 139753.0 -169966.0) 
                         (list 139781.0 -169944.0) 
                         (list 139803.0 -169916.0) 
                         (list 139816.0 -169883.0) 
                         (list 139821.0 -169848.0) 
                         (list 139821.0 -169393.0) 
                         (list 139816.0 -169358.0) 
                         (list 139803.0 -169325.0) 
                         (list 139781.0 -169297.0) 
                         (list 139753.0 -169275.0) 
                         (list 139720.0 -169262.0) 
                         (list 139685.0 -169257.0) 
                         (list 139649.0 -169262.0) 
                         (list 139617.0 -169275.0) 
                         (list 139588.0 -169297.0) 
                         (list 139567.0 -169325.0) 
                         (list 139553.0 -169358.0) 
                         (list 139548.0 -169393.0) 
                         (list 139548.0 -169710.0) 
                         (list 139187.0 -169710.0) 
                         (list 139187.0 -167420.0) 
                         (list 139685.0 -167420.0) 
                         (list 140184.0 -167420.0) 
                         (list 140184.0 -172353.0) 
                         (list 139187.0 -172353.0) 
                         (list 139187.0 -170500.0) 
                         (list 139548.0 -170500.0) 
                         (list 139548.0 -170757.0) 
                         (list 139553.0 -170792.0) 
                         (list 139567.0 -170825.0) 
                         (list 139588.0 -170853.0) 
                         (list 139617.0 -170875.0) 
                         (list 139649.0 -170889.0) 
                         (list 139685.0 -170893.0) 
                         (list 139720.0 -170889.0) 
                         (list 139753.0 -170875.0) 
                         (list 139781.0 -170853.0) 
                         (list 139803.0 -170825.0) 
                         (list 139816.0 -170792.0) 
                         (list 139821.0 -170757.0) 
                         (list 139821.0 -170302.0) 
                         (list 139816.0 -170267.0) 
                         (list 139803.0 -170234.0) 
                         (list 139781.0 -170206.0) 
                         (list 139753.0 -170184.0) 
                         (list 139720.0 -170171.0) 
                         (list 139685.0 -170166.0) 
                         (list 139649.0 -170171.0) 
                         (list 139617.0 -170184.0) 
                         (list 139588.0 -170206.0) 
                         (list 139567.0 -170234.0) 
                         (list 139553.0 -170267.0) 
                         (list 139548.0 -170302.0) 
                         (list 139548.0 -170500.0) 
                         (list 139187.0 -170500.0) 
                         (list 139187.0 -169710.0) 
                         "c"
         )
        (command "pline" (list 121035.0 -167420.0) "w" 0 0 
                         (list 121355.0 -167420.0) 
                         (list 121355.0 -171155.0) 
                         (list 119015.0 -171155.0) 
                         (list 119015.0 -169519.0) 
                         (list 119999.0 -169519.0) 
                         (list 119426.0 -170378.0) 
                         (list 119412.0 -170407.0) 
                         (list 119407.0 -170439.0) 
                         (list 119411.0 -170471.0) 
                         (list 119424.0 -170501.0) 
                         (list 119445.0 -170526.0) 
                         (list 119472.0 -170544.0) 
                         (list 119503.0 -170553.0) 
                         (list 119535.0 -170554.0) 
                         (list 119566.0 -170545.0) 
                         (list 119594.0 -170528.0) 
                         (list 119616.0 -170504.0) 
                         (list 121130.0 -168230.0) 
                         (list 121143.0 -168203.0) 
                         (list 121149.0 -168173.0) 
                         (list 121146.0 -168142.0) 
                         (list 121135.0 -168114.0) 
                         (list 121117.0 -168089.0) 
                         (list 121094.0 -168070.0) 
                         (list 121065.0 -168058.0) 
                         (list 121035.0 -168054.0) 
                         (list 120999.0 -168060.0) 
                         (list 120966.0 -168077.0) 
                         (list 120941.0 -168104.0) 
                         (list 119999.0 -169519.0) 
                         (list 119015.0 -169519.0) 
                         (list 119015.0 -167420.0) 
                         "c"
         )
        (command "pline" (list 112279.0 -167420.0) "w" 0 0 
                         (list 114056.0 -167420.0) 
                         (list 114655.0 -167420.0) 
                         (list 114655.0 -171155.0) 
                         (list 112279.0 -171155.0) 
                         (list 112279.0 -169228.0) 
                         (list 113175.0 -169228.0) 
                         (list 112446.0 -170323.0) 
                         (list 112432.0 -170352.0) 
                         (list 112427.0 -170384.0) 
                         (list 112431.0 -170416.0) 
                         (list 112444.0 -170445.0) 
                         (list 112465.0 -170470.0) 
                         (list 112492.0 -170488.0) 
                         (list 112523.0 -170498.0) 
                         (list 112555.0 -170498.0) 
                         (list 112586.0 -170490.0) 
                         (list 112614.0 -170473.0) 
                         (list 112635.0 -170449.0) 
                         (list 114150.0 -168175.0) 
                         (list 114164.0 -168147.0) 
                         (list 114169.0 -168117.0) 
                         (list 114166.0 -168087.0) 
                         (list 114156.0 -168058.0) 
                         (list 114138.0 -168033.0) 
                         (list 114114.0 -168014.0) 
                         (list 114086.0 -168002.0) 
                         (list 114056.0 -167998.0) 
                         (list 114019.0 -168004.0) 
                         (list 113986.0 -168022.0) 
                         (list 113961.0 -168049.0) 
                         (list 113175.0 -169228.0) 
                         (list 112279.0 -169228.0) 
                         "c"
         )
  )

(DEFUN C:mmms( / );id id_len n m id_c ss dep_x2 dt_id c_date )
  (setvar "osmode" 0)
  (setvar "orthomode" 0)
  (draw_edge1)
  (setq id(getstring"请输入流程单号："))
  (setq id_len(strlen id))
  (setq n 0)
  (setq m 1)
  (while(<= m id_len)
       (setq id_c(substr id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq ss(ssget"w"'(-1374 -2466.47)'(1374 2466.47)))
       (setq dep_x (+ 138809 (* m 2748)))
       (command "move" ss ""  "0,0"  (list dep_x -169886.5)"")
   
       (setq m (+ m 1))
 )
  (setq c_date(getvar "cdate"))
  (setq dt_id (itoa (fix c_date)))
  (setq m 1)
  (while(<= m 4)
       (setq id_c(substr dt_id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq s1(ssget"w"'(-1374 -2466.47)'(1374 2466.47)))
       (command "layer""n""ok""")
       (command "change"s1"""p""la""ok""")
	(scale "ok" ke kf)
        (command "change"s1"""p""la""0""")			    
       (setq dep_x2 (+ 102469 (* m 2180)))
       (command "move" s1 ""   "0,0"  (list dep_x2 -169287.6)"")
       (setq m (+ m 1))
  )
  (setq m 5)
  (while(<= m 6)
       (setq id_c(substr dt_id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq s2(ssget"w"'(-1374 -2466.47)'(1374 2466.47)))
       (command "layer""n""ok""")
       (command "change"s2"""p""la""ok""")
	(scale "ok" ke kf)
        (command "change"s2"""p""la""0""")			    
       (setq dep_x2 (+ 104845 (* m 2180)))
       (command "move" s2 ""   "0,0"  (list dep_x2 -169287.6)"")
       (setq m (+ m 1))
  )
  (setq m 7)
  (while(<= m 8)
       (setq id_c(substr dt_id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq s3(ssget"w"'(-1374 -2466.47)'(1374 2466.47)))
       (command "layer""n""ok""")
       (command "change"s3"""p""la""ok""")
	(scale "ok" ke kf)
        (command "change"s3"""p""la""0""")			    
       (setq dep_x2 (+ 107184.49 (* m 2180)))
       (command "move" s3 ""   "0,0"  (list dep_x2 -169287.6)"")
       (setq m (+ m 1))
  )
  
  (setq ly_name (getstring"请输入一层有效层名："))
  (command "layer""n" ly_name "")
  (command "change""all""""p""la" ly_name"""")
  (command "layer""lock"ly_name"")
  (command "clear""")
  (command "layer""unlock"ly_name"")
  (command "zoom""e""")
  (prompt"请再次确认流程单号：")
  (strcat id)
  
 )
(defun zero () 
        (command "pline" (list -266.804 2466.47) "w" 0 0 
                         (list 44.3028 2466.47) 
                         (list 1374.0 2466.47) 
                         (list 1374.0 -2466.47) 
                         (list -1374.0 -2466.47) 
                         (list -1374.0 2466.47) 
                         (list -409.979 2466.47) 
                         (list -266.814 2466.47) 
                         (list -266.814 1480.75) 
                         (list -409.979 1480.75) 
                         (list -445.314 1476.09) 
                         (list -478.237 1462.44) 
                         (list -506.498 1440.72) 
                         (list -960.78 985.692) 
                         (list -982.412 957.46) 
                         (list -996.01 924.594) 
                         (list -1000.65 889.331) 
                         (list -1000.65 -929.289) 
                         (list -996.01 -964.553) 
                         (list -982.412 -997.418) 
                         (list -960.78 -1025.65) 
                         (list -506.498 -1480.68) 
                         (list -478.237 -1502.4) 
                         (list -445.314 -1516.05) 
                         (list -409.979 -1520.71) 
                         (list 44.3028 -1520.71) 
                         (list 79.6025 -1516.06) 
                         (list 112.497 -1502.43) 
                         (list 140.743 -1480.76) 
                         (list 595.772 -1025.73) 
                         (list 617.446 -997.483) 
                         (list 631.072 -964.589) 
                         (list 635.719 -929.289) 
                         (list 635.719 889.331) 
                         (list 631.072 924.63) 
                         (list 617.446 957.524) 
                         (list 595.772 985.771) 
                         (list 140.743 1440.8) 
                         (list 112.497 1462.47) 
                         (list 79.6025 1476.1) 
                         (list 44.3028 1480.75) 
                         (list -266.804 1480.75) 
                         "c"
         )
        (command "pline" (list 362.944 832.837) "w" 0 0 
                         (list 362.944 -872.796) 
                         (list -12.1907 -1247.93) 
                         (list -353.419 -1247.93) 
                         (list -727.873 -872.861) 
                         (list -727.873 832.903) 
                         (list -353.419 1207.97) 
                         (list -12.1907 1207.97) 
                         "c"
         )
  )
(defun one () 
        (command "pline" (list -538.901 -1520.71) "w" 0 0 
                         (list 60.7103 -1520.71) 
                         (list 96.0099 -1516.06) 
                         (list 128.904 -1502.43) 
                         (list 157.151 -1480.76) 
                         (list 178.825 -1452.51) 
                         (list 192.45 -1419.62) 
                         (list 197.098 -1384.32) 
                         (list 192.45 -1349.02) 
                         (list 178.825 -1316.12) 
                         (list 157.151 -1287.88) 
                         (list 128.904 -1266.2) 
                         (list 96.0099 -1252.58) 
                         (list 60.7103 -1247.93) 
                         (list -257.184 -1247.93) 
                         (list -257.184 1344.36) 
                         (list -261.831 1379.66) 
                         (list -275.456 1412.55) 
                         (list -297.131 1440.8) 
                         (list -325.377 1462.47) 
                         (list -358.271 1476.1) 
                         (list -393.571 1480.75) 
                         (list -428.871 1476.1) 
                         (list -461.765 1462.47) 
                         (list -490.012 1440.8) 
                         (list -945.04 985.771) 
                         (list -966.715 957.524) 
                         (list -980.34 924.63) 
                         (list -984.987 889.331) 
                         (list -980.34 854.031) 
                         (list -966.715 821.137) 
                         (list -945.04 792.89) 
                         (list -916.793 771.216) 
                         (list -883.899 757.591) 
                         (list -848.6 752.943) 
                         (list -813.3 757.591) 
                         (list -780.406 771.216) 
                         (list -752.159 792.89) 
                         (list -529.958 1015.09) 
                         (list -529.958 -1247.93) 
                         (list -848.6 -1247.93) 
                         (list -883.899 -1252.58) 
                         (list -916.793 -1266.2) 
                         (list -945.04 -1287.88) 
                         (list -966.715 -1316.12) 
                         (list -980.34 -1349.02) 
                         (list -984.987 -1384.32) 
                         (list -980.34 -1419.62) 
                         (list -966.715 -1452.51) 
                         (list -945.04 -1480.76) 
                         (list -916.793 -1502.43) 
                         (list -883.899 -1516.06) 
                         (list -848.6 -1520.71) 
                         (list -538.911 -1520.71) 
                         (list -538.911 -2466.47) 
                         (list -1374.0 -2466.47) 
                         (list -1374.0 2466.47) 
                         (list -393.571 2466.47) 
                         (list 1374.0 2466.47) 
                         (list 1374.0 -2466.47) 
                         (list -538.901 -2466.47) 
                         "c"
         )
  )
(defun two () 
        (command "pline" (list 27.6798 2466.47) "w" 0 0 
                         (list 631.765 2466.47) 
                         (list 1374.0 2466.47) 
                         (list 1374.0 -2466.47) 
                         (list -1374.0 -2466.47) 
                         (list -1374.0 2466.47) 
                         (list 27.6698 2466.47) 
                         (list 27.6698 1455.21) 
                         (list -276.798 1455.21) 
                         (list -312.133 1450.55) 
                         (list -345.056 1436.9) 
                         (list -373.317 1415.19) 
                         (list -827.599 960.157) 
                         (list -849.25 931.892) 
                         (list -862.848 898.987) 
                         (list -867.466 863.684) 
                         (list -862.79 828.388) 
                         (list -849.138 795.505) 
                         (list -827.44 767.276) 
                         (list -799.176 745.625) 
                         (list -766.27 732.027) 
                         (list -730.967 727.408) 
                         (list -695.671 732.085) 
                         (list -662.788 745.737) 
                         (list -634.559 767.435) 
                         (list -220.238 1182.44) 
                         (list 575.206 1182.44) 
                         (list 949.659 807.368) 
                         (list 949.659 465.942) 
                         (list 575.206 90.8731) 
                         (list -276.798 90.8731) 
                         (list -312.133 86.2162) 
                         (list -345.056 72.5633) 
                         (list -373.317 50.8469) 
                         (list -827.599 -404.182) 
                         (list -849.231 -432.414) 
                         (list -862.829 -465.279) 
                         (list -867.466 -500.543) 
                         (list -867.466 -1409.85) 
                         (list -862.819 -1445.15) 
                         (list -849.194 -1478.05) 
                         (list -827.519 -1506.29) 
                         (list -799.273 -1527.97) 
                         (list -766.379 -1541.59) 
                         (list -731.079 -1546.24) 
                         (list 1086.05 -1546.24) 
                         (list 1121.35 -1541.59) 
                         (list 1154.24 -1527.97) 
                         (list 1182.49 -1506.29) 
                         (list 1204.16 -1478.05) 
                         (list 1217.79 -1445.15) 
                         (list 1222.43 -1409.85) 
                         (list 1217.79 -1374.55) 
                         (list 1204.16 -1341.66) 
                         (list 1182.49 -1313.41) 
                         (list 1154.24 -1291.74) 
                         (list 1121.35 -1278.11) 
                         (list 1086.05 -1273.47) 
                         (list -594.692 -1273.47) 
                         (list -594.692 -556.971) 
                         (list -220.238 -181.902) 
                         (list 631.765 -181.902) 
                         (list 667.101 -177.245) 
                         (list 700.024 -163.592) 
                         (list 728.285 -141.875) 
                         (list 1182.57 313.153) 
                         (list 1204.2 341.385) 
                         (list 1217.8 374.251) 
                         (list 1222.43 409.514) 
                         (list 1222.43 863.796) 
                         (list 1217.8 899.059) 
                         (list 1204.2 931.925) 
                         (list 1182.57 960.157) 
                         (list 728.285 1415.19) 
                         (list 700.024 1436.9) 
                         (list 667.101 1450.55) 
                         (list 631.765 1455.21) 
                         (list 27.6798 1455.21) 
                         "c"
         )
  )
(defun three () 
        (command "pline" (list 45.5618 2466.47) "w" 0 0 
                         (list 631.765 2466.47) 
                         (list 654.359 2466.47) 
                         (list 1374.0 2466.47) 
                         (list 1374.0 -2466.47) 
                         (list -1374.0 -2466.47) 
                         (list -1374.0 2466.47) 
                         (list -242.797 2466.47) 
                         (list 45.5518 2466.47) 
                         (list 45.5518 1466.94) 
                         (list -242.789 1466.94) 
                         (list -282.719 1461.68) 
                         (list -319.918 1446.27) 
                         (list -351.858 1421.75) 
                         (list -800.432 972.921) 
                         (list -823.35 943.652) 
                         (list -838.597 909.749) 
                         (list -845.288 873.183) 
                         (list -843.034 836.078) 
                         (list -831.965 800.59) 
                         (list -812.725 768.783) 
                         (list -786.432 742.504) 
                         (list -754.615 723.281) 
                         (list -719.121 712.231) 
                         (list -682.015 709.997) 
                         (list -645.452 716.707) 
                         (list -611.557 731.973) 
                         (list -582.301 754.907) 
                         (list -178.895 1158.54) 
                         (list 590.464 1158.54) 
                         (list 948.733 800.069) 
                         (list 948.733 478.679) 
                         (list 590.464 120.207) 
                         (list 205.785 120.207) 
                         (list 168.882 115.726) 
                         (list 134.124 102.544) 
                         (list 103.531 81.4275) 
                         (list 78.8805 53.6027) 
                         (list 61.6051 20.6872) 
                         (list 52.7089 -15.4061) 
                         (list 52.7089 -52.5796) 
                         (list 61.6051 -88.6729) 
                         (list 78.8805 -121.588) 
                         (list 103.531 -149.413) 
                         (list 134.124 -170.53) 
                         (list 168.882 -183.712) 
                         (list 205.785 -188.193) 
                         (list 590.464 -188.193) 
                         (list 948.733 -546.665) 
                         (list 948.733 -868.048) 
                         (list 590.464 -1226.53) 
                         (list -178.895 -1226.53) 
                         (list -582.301 -822.892) 
                         (list -611.556 -799.959) 
                         (list -645.45 -784.693) 
                         (list -682.013 -777.982) 
                         (list -719.119 -780.216) 
                         (list -754.612 -791.265) 
                         (list -786.429 -810.487) 
                         (list -812.722 -836.765) 
                         (list -831.962 -868.572) 
                         (list -843.031 -904.058) 
                         (list -845.286 -941.163) 
                         (list -838.596 -977.729) 
                         (list -823.349 -1011.63) 
                         (list -800.432 -1040.9) 
                         (list -351.858 -1489.73) 
                         (list -319.917 -1514.25) 
                         (list -282.715 -1529.67) 
                         (list -242.789 -1534.93) 
                         (list 654.359 -1534.93) 
                         (list 694.284 -1529.67) 
                         (list 731.486 -1514.25) 
                         (list 763.427 -1489.73) 
                         (list 1212.0 -1040.9) 
                         (list 1236.49 -1008.97) 
                         (list 1251.88 -971.793) 
                         (list 1257.13 -931.899) 
                         (list 1257.13 -482.82) 
                         (list 1251.88 -442.924) 
                         (list 1236.49 -405.745) 
                         (list 1212.0 -373.813) 
                         (list 872.367 -33.9928) 
                         (list 1212.0 305.827) 
                         (list 1236.49 337.759) 
                         (list 1251.88 374.938) 
                         (list 1257.13 414.834) 
                         (list 1257.13 863.914) 
                         (list 1251.88 903.809) 
                         (list 1236.49 940.989) 
                         (list 1212.0 972.921) 
                         (list 763.427 1421.75) 
                         (list 731.485 1446.27) 
                         (list 694.283 1461.68) 
                         (list 654.359 1466.94) 
                         (list 45.5618 1466.94) 
                         "c"
         )
  )
(defun four () 
        (command "pline" (list -408.672 -2466.47) "w" 0 0 
                         (list -1374.0 -2466.47) 
                         (list -1374.0 2466.47) 
                         (list -704.949 2466.47) 
                         (list 436.77 2466.47) 
                         (list 539.654 2466.47) 
                         (list 1374.0 2466.47) 
                         (list 1374.0 -2466.47) 
                         (list -408.662 -2466.47) 
                         (list -408.662 -633.361) 
                         (list 385.453 -633.361) 
                         (list 385.453 -1377.07) 
                         (list 389.934 -1413.97) 
                         (list 403.115 -1448.73) 
                         (list 424.232 -1479.32) 
                         (list 452.057 -1503.97) 
                         (list 484.973 -1521.25) 
                         (list 521.066 -1530.14) 
                         (list 558.239 -1530.14) 
                         (list 594.333 -1521.25) 
                         (list 627.248 -1503.97) 
                         (list 655.073 -1479.32) 
                         (list 676.19 -1448.73) 
                         (list 689.372 -1413.97) 
                         (list 693.853 -1377.07) 
                         (list 693.853 -633.361) 
                         (list 988.227 -633.361) 
                         (list 1025.13 -628.88) 
                         (list 1059.89 -615.699) 
                         (list 1090.48 -594.582) 
                         (list 1115.13 -566.757) 
                         (list 1132.41 -533.841) 
                         (list 1141.3 -497.748) 
                         (list 1141.3 -460.575) 
                         (list 1132.41 -424.481) 
                         (list 1115.13 -391.566) 
                         (list 1090.48 -363.741) 
                         (list 1059.89 -342.624) 
                         (list 1025.13 -329.442) 
                         (list 988.227 -324.961) 
                         (list 693.853 -324.961) 
                         (list 693.853 1316.4) 
                         (list 688.599 1356.31) 
                         (list 673.195 1393.5) 
                         (list 648.69 1425.44) 
                         (list 616.754 1449.94) 
                         (list 579.564 1465.35) 
                         (list 539.654 1470.6) 
                         (list 504.213 1466.47) 
                         (list 470.67 1454.31) 
                         (list 440.82 1434.76) 
                         (list 416.262 1408.88) 
                         (list -929.466 -386.684) 
                         (list -948.271 -419.518) 
                         (list -958.513 -455.942) 
                         (list -959.578 -493.763) 
                         (list -951.4 -530.706) 
                         (list -934.473 -564.545) 
                         (list -909.815 -593.243) 
                         (list -878.91 -615.072) 
                         (list -843.62 -628.719) 
                         (list -806.069 -633.361) 
                         (list -408.672 -633.361) 
                         "c"
         )
        (command "pline" (list 385.453 853.54) "w" 0 0 
                         (list -497.799 -324.961) 
                         (list 385.453 -324.961) 
                         "c"
         )
  )
(defun five () 
        (command "pline" (list 17.8963 2466.47) "w" 0 0 
                         (list 436.77 2466.47) 
                         (list 1374.0 2466.47) 
                         (list 1374.0 -2466.47) 
                         (list -1374.0 -2466.47) 
                         (list -1374.0 2466.47) 
                         (list -704.949 2466.47) 
                         (list 17.8863 2466.47) 
                         (list 17.8863 1500.99) 
                         (list -704.949 1500.99) 
                         (list -744.859 1495.74) 
                         (list -782.048 1480.33) 
                         (list -813.984 1455.83) 
                         (list -838.489 1423.89) 
                         (list -853.894 1386.7) 
                         (list -859.149 1346.79) 
                         (list -859.149 448.884) 
                         (list -853.894 408.974) 
                         (list -838.489 371.785) 
                         (list -813.984 339.849) 
                         (list -782.048 315.344) 
                         (list -744.859 299.939) 
                         (list -704.949 294.684) 
                         (list 576.878 294.684) 
                         (list 935.147 -63.7879) 
                         (list 935.147 -833.998) 
                         (list 576.878 -1192.48) 
                         (list -192.481 -1192.48) 
                         (list -595.887 -788.842) 
                         (list -625.142 -765.909) 
                         (list -659.036 -750.643) 
                         (list -695.598 -743.932) 
                         (list -732.704 -746.166) 
                         (list -768.198 -757.215) 
                         (list -800.015 -776.437) 
                         (list -826.308 -802.715) 
                         (list -845.548 -834.522) 
                         (list -856.617 -870.008) 
                         (list -858.872 -907.113) 
                         (list -852.182 -943.679) 
                         (list -836.935 -977.582) 
                         (list -814.018 -1006.85) 
                         (list -365.444 -1455.68) 
                         (list -333.502 -1480.2) 
                         (list -296.3 -1495.62) 
                         (list -256.375 -1500.88) 
                         (list 640.773 -1500.88) 
                         (list 680.698 -1495.62) 
                         (list 717.9 -1480.2) 
                         (list 749.841 -1455.68) 
                         (list 1198.42 -1006.85) 
                         (list 1222.9 -974.92) 
                         (list 1238.29 -937.743) 
                         (list 1243.55 -897.85) 
                         (list 1243.55 0.0570701) 
                         (list 1238.3 39.9528) 
                         (list 1222.9 77.1321) 
                         (list 1198.42 109.064) 
                         (list 749.841 557.891) 
                         (list 717.899 582.413) 
                         (list 680.697 597.827) 
                         (list 640.773 603.084) 
                         (list -550.749 603.084) 
                         (list -550.749 1192.59) 
                         (list 1089.35 1192.59) 
                         (list 1126.25 1197.07) 
                         (list 1161.01 1210.25) 
                         (list 1191.6 1231.37) 
                         (list 1216.25 1259.19) 
                         (list 1233.53 1292.11) 
                         (list 1242.42 1328.2) 
                         (list 1242.42 1365.38) 
                         (list 1233.53 1401.47) 
                         (list 1216.25 1434.39) 
                         (list 1191.6 1462.21) 
                         (list 1161.01 1483.33) 
                         (list 1126.25 1496.51) 
                         (list 1089.35 1500.99) 
                         (list 17.8963 1500.99) 
                         "c"
         )
  )
(defun six () 
        (command "pline" (list 26.3687 -1522.27) "w" 0 0 
                         (list 720.721 -1522.27) 
                         (list 760.646 -1517.01) 
                         (list 797.848 -1501.6) 
                         (list 829.79 -1477.07) 
                         (list 1278.36 -1028.25) 
                         (list 1302.85 -996.316) 
                         (list 1318.24 -959.139) 
                         (list 1323.49 -919.245) 
                         (list 1323.49 -470.166) 
                         (list 1318.24 -430.27) 
                         (list 1302.85 -393.091) 
                         (list 1278.36 -361.159) 
                         (list 829.79 87.6682) 
                         (list 797.847 112.19) 
                         (list 760.645 127.605) 
                         (list 720.721 132.861) 
                         (list -470.801 132.861) 
                         (list -470.801 363.655) 
                         (list 336.053 1171.19) 
                         (list 720.721 1171.19) 
                         (list 757.623 1175.68) 
                         (list 792.381 1188.86) 
                         (list 822.974 1209.97) 
                         (list 847.625 1237.8) 
                         (list 864.9 1270.71) 
                         (list 873.796 1306.81) 
                         (list 873.796 1343.98) 
                         (list 864.9 1380.07) 
                         (list 847.625 1412.99) 
                         (list 822.974 1440.81) 
                         (list 792.381 1461.93) 
                         (list 757.623 1475.11) 
                         (list 720.721 1479.59) 
                         (list 272.147 1479.59) 
                         (list 232.216 1474.33) 
                         (list 195.01 1458.91) 
                         (list 163.066 1434.38) 
                         (list -734.088 536.477) 
                         (list -758.567 504.549) 
                         (list -773.954 467.376) 
                         (list -779.201 427.488) 
                         (list -779.201 -919.245) 
                         (list -773.949 -959.139) 
                         (list -758.556 -996.316) 
                         (list -734.07 -1028.25) 
                         (list -285.496 -1477.07) 
                         (list -253.554 -1501.6) 
                         (list -216.352 -1517.01) 
                         (list -176.427 -1522.27) 
                         (list 26.3587 -1522.27) 
                         (list 26.3587 -2466.47) 
                         (list -1374.0 -2466.47) 
                         (list -1374.0 2466.47) 
                         (list -704.949 2466.47) 
                         (list 272.147 2466.47) 
                         (list 436.77 2466.47) 
                         (list 1374.0 2466.47) 
                         (list 1374.0 -2466.47) 
                         (list 26.3687 -2466.47) 
                         "c"
         )
        (command "pline" (list -470.801 -855.394) "w" 0 0 
                         (list -112.533 -1213.87) 
                         (list 656.826 -1213.87) 
                         (list 1015.09 -855.394) 
                         (list 1015.09 -534.011) 
                         (list 656.826 -175.539) 
                         (list -470.801 -175.539) 
                         "c"
         )
  )
(defun seven () 
        (command "pline" (list 101.938 2466.47) "w" 0 0 
                         (list 436.77 2466.47) 
                         (list 1151.04 2466.47) 
                         (list 1374.0 2466.47) 
                         (list 1374.0 -2466.47) 
                         (list -1374.0 -2466.47) 
                         (list -1374.0 2466.47) 
                         (list -704.949 2466.47) 
                         (list -643.258 2466.47) 
                         (list 101.928 2466.47) 
                         (list 101.928 1460.51) 
                         (list -643.258 1460.51) 
                         (list -680.161 1456.03) 
                         (list -714.919 1442.85) 
                         (list -745.512 1421.73) 
                         (list -770.162 1393.91) 
                         (list -787.438 1360.99) 
                         (list -796.334 1324.9) 
                         (list -796.334 1287.72) 
                         (list -787.438 1251.63) 
                         (list -770.162 1218.72) 
                         (list -745.512 1190.89) 
                         (list -714.919 1169.77) 
                         (list -680.161 1156.59) 
                         (list -643.258 1152.11) 
                         (list 901.622 1152.11) 
                         (list -332.625 -1318.23) 
                         (list -345.11 -1353.25) 
                         (list -348.853 -1390.23) 
                         (list -343.636 -1427.04) 
                         (list -329.762 -1461.53) 
                         (list -308.039 -1491.69) 
                         (list -279.727 -1515.78) 
                         (list -246.473 -1532.39) 
                         (list -210.209 -1540.57) 
                         (list -173.043 -1539.83) 
                         (list -137.135 -1530.21) 
                         (list -104.571 -1512.28) 
                         (list -77.2447 -1487.08) 
                         (list -56.7432 -1456.07) 
                         (list 1288.98 1237.39) 
                         (list 1301.88 1274.3) 
                         (list 1305.08 1313.27) 
                         (list 1298.37 1351.8) 
                         (list 1282.19 1387.4) 
                         (list 1257.58 1417.78) 
                         (list 1226.12 1441.0) 
                         (list 1189.82 1455.55) 
                         (list 1151.04 1460.51) 
                         (list 101.938 1460.51) 
                         "c"
         )
  )
(defun eight () 
        (command "pline" (list 392.798 202.5) "w" 0 0 
                         (list 751.066 560.972) 
                         (list 751.066 882.362) 
                         (list 392.798 1240.83) 
                         (list -376.561 1240.83) 
                         (list -734.83 882.362) 
                         (list -734.83 560.972) 
                         (list -376.561 202.5) 
                         "c"
         )
        (command "pline" (list -376.561 -105.9) "w" 0 0 
                         (list -734.83 -464.371) 
                         (list -734.83 -785.755) 
                         (list -376.561 -1144.23) 
                         (list 392.798 -1144.23) 
                         (list 751.066 -785.755) 
                         (list 751.066 -464.371) 
                         (list 392.798 -105.9) 
                         "c"
         )
        (command "pline" (list -480.385 1543.98) "w" 0 0 
                         (list -517.584 1528.56) 
                         (list -549.524 1504.04) 
                         (list -998.098 1055.21) 
                         (list -1022.58 1023.28) 
                         (list -1037.98 986.103) 
                         (list -1043.23 946.207) 
                         (list -1043.23 497.127) 
                         (list -1037.98 457.232) 
                         (list -1022.58 420.052) 
                         (list -998.098 388.12) 
                         (list -658.47 48.3004) 
                         (list -998.098 -291.519) 
                         (list -1022.58 -323.451) 
                         (list -1037.98 -360.631) 
                         (list -1043.23 -400.526) 
                         (list -1043.23 -849.606) 
                         (list -1037.98 -889.5) 
                         (list -1022.58 -926.677) 
                         (list -998.098 -958.607) 
                         (list -549.524 -1407.43) 
                         (list -517.583 -1431.96) 
                         (list -480.381 -1447.37) 
                         (list -440.456 -1452.63) 
                         (list 456.692 -1452.63) 
                         (list 496.618 -1447.37) 
                         (list 533.82 -1431.96) 
                         (list 565.761 -1407.43) 
                         (list 1014.34 -958.607) 
                         (list 1038.82 -926.677) 
                         (list 1054.21 -889.5) 
                         (list 1059.47 -849.606) 
                         (list 1059.47 -400.526) 
                         (list 1054.21 -360.631) 
                         (list 1038.82 -323.451) 
                         (list 1014.34 -291.519) 
                         (list 674.7 48.3004) 
                         (list 1014.34 388.12) 
                         (list 1038.82 420.052) 
                         (list 1054.21 457.232) 
                         (list 1059.47 497.127) 
                         (list 1059.47 946.207) 
                         (list 1054.21 986.103) 
                         (list 1038.82 1023.28) 
                         (list 1014.34 1055.21) 
                         (list 565.761 1504.04) 
                         (list 533.819 1528.56) 
                         (list 496.617 1543.98) 
                         (list 456.692 1549.23) 
                         (list -96.8628 1549.23) 
                         (list -96.8628 2466.47) 
                         (list 436.77 2466.47) 
                         (list 456.692 2466.47) 
                         (list 1374.0 2466.47) 
                         (list 1374.0 -2466.47) 
                         (list -1374.0 -2466.47) 
                         (list -1374.0 2466.47) 
                         (list -704.949 2466.47) 
                         (list -172.616 2466.47) 
                         (list -96.8728 2466.47) 
                         (list -96.8728 1549.23) 
                         (list -440.456 1549.23) 
                         "c"
         )
  )
(defun nine () 
        (command "pline" (list -143.815 2466.47) "w" 0 0 
                         (list 436.77 2466.47) 
                         (list 1374.0 2466.47) 
                         (list 1374.0 -2466.47) 
                         (list -1374.0 -2466.47) 
                         (list -1374.0 2466.47) 
                         (list -143.825 2466.47) 
                         (list -143.825 1482.31) 
                         (list -471.793 1482.31) 
                         (list -507.129 1477.66) 
                         (list -540.052 1464.0) 
                         (list -568.313 1442.29) 
                         (list -1022.59 987.26) 
                         (list -1044.23 959.028) 
                         (list -1057.82 926.162) 
                         (list -1062.46 890.899) 
                         (list -1062.46 436.617) 
                         (list -1057.82 401.354) 
                         (list -1044.23 368.488) 
                         (list -1022.59 340.256) 
                         (list -568.313 -114.773) 
                         (list -540.052 -136.489) 
                         (list -507.129 -150.142) 
                         (list -471.793 -154.799) 
                         (list 754.664 -154.799) 
                         (list 754.664 -416.979) 
                         (list -74.0382 -1246.36) 
                         (list -471.793 -1246.36) 
                         (list -507.093 -1251.01) 
                         (list -539.987 -1264.64) 
                         (list -568.234 -1286.31) 
                         (list -589.908 -1314.56) 
                         (list -603.533 -1347.45) 
                         (list -608.181 -1382.75) 
                         (list -603.533 -1418.05) 
                         (list -589.908 -1450.94) 
                         (list -568.234 -1479.19) 
                         (list -539.987 -1500.86) 
                         (list -507.093 -1514.49) 
                         (list -471.793 -1519.14) 
                         (list -17.5118 -1519.14) 
                         (list 17.8059 -1514.49) 
                         (list 50.7142 -1500.85) 
                         (list 78.9682 -1479.15) 
                         (list 987.531 -569.841) 
                         (list 1009.18 -541.601) 
                         (list 1022.8 -508.722) 
                         (list 1027.44 -473.44) 
                         (list 1027.44 890.899) 
                         (list 1022.8 926.162) 
                         (list 1009.2 959.028) 
                         (list 987.571 987.26) 
                         (list 533.289 1442.29) 
                         (list 505.028 1464.0) 
                         (list 472.105 1477.66) 
                         (list 436.77 1482.31) 
                         (list -143.815 1482.31) 
                         "c"
         )
        (command "pline" (list -415.234 1209.54) "w" 0 0 
                         (list 380.21 1209.54) 
                         (list 754.664 834.471) 
                         (list 754.664 117.976) 
                         (list -415.234 117.976) 
                         (list -789.687 493.045) 
                         (list -789.687 834.471) 
                         "c"
         )
  )

(defun scale (layer_name ke kf)
    (setq ke 0.76)
    (setq kf 0.793304)
    
    (setq
      ss_lwpl (ssget "x"
		     (list (cons 0 "lwpolyline") (cons 8 layer_name))
	      )
    )
    (if	ss_lwpl
      (progn
	(setq ss_cnt (sslength ss_lwpl))
	(setq i_loop 0)
	(while (< i_loop ss_cnt)
	  (setq pl_dt (entget (ssname ss_lwpl i_loop)))
	  (setq dt nil)
	  (while pl_dt
	    (if	(/= (caar pl_dt) 10)
	      (setq dt (append dt (list (car pl_dt))))
	      (progn
		(setq scl_x (*(cadar pl_dt) kf))
		(setq scl_y (* (caddar pl_dt) ke))
		(setq
		  dt (append dt (list (cons 10 (list scl_x scl_y 0))))
		)
	      )
	    )
	    (setq pl_dt (cdr pl_dt))
	  )
	  (entmod dt)
	  (setq i_loop (1+ i_loop))
        )
     ) 
    )
   
    
);        defun scale(layer_name ke)
(defun draw_edge () 
        (command "pline" (list 212997.0 -187500.0) "w" 0 0 
                         (list 215950.0 -187500.0) 
                         (list 215950.0 187500.0) 
                         (list 212997.0 187500.0) 
                         "c"
         )
        (command "pline" (list -215950.0 -187500.0) "w" 0 0 
                         (list -212997.0 -187500.0) 
                         (list -212997.0 187500.0) 
                         (list -215950.0 187500.0) 
                         "c"
         )
        (command "pline" (list 200666.0 -202950.0) "w" 0 0 
                         (list 211450.0 -202950.0) 
                         (list 211450.0 -193050.0) 
                         (list 200666.0 -193050.0) 
                         "c"
         )
        (command "pline" (list 125117.0 -200303.0) "w" 0 0 
                         (list 132779.0 -200303.0) 
                         (list 132779.0 -195370.0) 
                         (list 125117.0 -195370.0) 
                         "c"
         )
        (command "pline" (list 162165.0 -200303.0) "w" 0 0 
                         (list 171018.0 -200303.0) 
                         (list 171018.0 -195370.0) 
                         (list 162165.0 -195370.0) 
                         "c"
         )
        (command "pline" (list 193121.0 -200303.0) "w" 0 0 
                         (list 200666.0 -200303.0) 
                         (list 200666.0 -195370.0) 
                         (list 193121.0 -195370.0) 
                         "c"
         )
        (command "pline" (list 160742.0 -199105.0) "w" 0 0 
                         (list 160660.0 -199105.0) 
                         (list 160660.0 -199347.0) 
                         (list 140742.0 -199347.0) 
                         (list 140742.0 -199385.0) 
                         (list 160660.0 -199385.0) 
                         (list 160660.0 -199105.0) 
                         (list 160588.0 -199105.0) 
                         (list 160588.0 -199272.0) 
                         (list 140742.0 -199272.0) 
                         (list 140742.0 -199310.0) 
                         (list 160588.0 -199310.0) 
                         (list 160588.0 -199105.0) 
                         (list 140009.0 -199105.0) 
                         (list 140009.0 -200303.0) 
                         (list 162165.0 -200303.0) 
                         (list 162165.0 -199105.0) 
                         (list 160742.0 -199105.0) 
                         (list 160742.0 -199422.0) 
                         (list 140742.0 -199422.0) 
                         (list 140742.0 -199460.0) 
                         (list 160742.0 -199460.0) 
                         "c"
         )
        (command "pline" (list 125117.0 -202950.0) "w" 0 0 
                         (list 200666.0 -202950.0) 
                         (list 200666.0 -200303.0) 
                         (list 125117.0 -200303.0) 
                         "c"
         )
        (command "pline" (list 125117.0 -195370.0) "w" 0 0 
                         (list 200666.0 -195370.0) 
                         (list 200666.0 -193050.0) 
                         (list 125117.0 -193050.0) 
                         "c"
         )
        (command "pline" (list 162164.0 -199105.0) "w" 0 0 
                         (list 162165.0 -199105.0) 
                         (list 162165.0 -195370.0) 
                         (list 162164.0 -195370.0) 
                         "c"
         )
        (command "pline" (list 133854.0 -196387.0) "w" 0 0 
                         (list 133400.0 -196841.0) 
                         (list 133378.0 -196870.0) 
                         (list 133365.0 -196903.0) 
                         (list 133360.0 -196938.0) 
                         (list 133365.0 -196973.0) 
                         (list 133378.0 -197006.0) 
                         (list 133400.0 -197034.0) 
                         (list 135120.0 -198756.0) 
                         (list 134802.0 -199074.0) 
                         (list 134007.0 -199074.0) 
                         (list 133593.0 -198659.0) 
                         (list 133565.0 -198638.0) 
                         (list 133532.0 -198624.0) 
                         (list 133496.0 -198620.0) 
                         (list 133461.0 -198624.0) 
                         (list 133428.0 -198638.0) 
                         (list 133400.0 -198659.0) 
                         (list 133378.0 -198688.0) 
                         (list 133365.0 -198720.0) 
                         (list 133360.0 -198756.0) 
                         (list 133365.0 -198791.0) 
                         (list 133378.0 -198824.0) 
                         (list 133400.0 -198852.0) 
                         (list 133854.0 -199307.0) 
                         (list 133882.0 -199328.0) 
                         (list 133915.0 -199342.0) 
                         (list 133950.0 -199347.0) 
                         (list 134859.0 -199347.0) 
                         (list 134894.0 -199342.0) 
                         (list 134927.0 -199328.0) 
                         (list 134955.0 -199307.0) 
                         (list 135409.0 -198852.0) 
                         (list 135431.0 -198824.0) 
                         (list 135444.0 -198791.0) 
                         (list 135449.0 -198756.0) 
                         (list 135444.0 -198721.0) 
                         (list 135431.0 -198688.0) 
                         (list 135409.0 -198659.0) 
                         (list 133689.0 -196938.0) 
                         (list 134007.0 -196620.0) 
                         (list 134802.0 -196620.0) 
                         (list 135216.0 -197034.0) 
                         (list 135245.0 -197056.0) 
                         (list 135277.0 -197069.0) 
                         (list 135313.0 -197074.0) 
                         (list 135348.0 -197069.0) 
                         (list 135381.0 -197056.0) 
                         (list 135409.0 -197034.0) 
                         (list 135431.0 -197006.0) 
                         (list 135444.0 -196973.0) 
                         (list 135449.0 -196938.0) 
                         (list 135444.0 -196903.0) 
                         (list 135431.0 -196870.0) 
                         (list 135409.0 -196841.0) 
                         (list 134955.0 -196387.0) 
                         (list 134927.0 -196365.0) 
                         (list 134894.0 -196352.0) 
                         (list 134859.0 -196347.0) 
                         (list 134241.0 -196347.0) 
                         (list 134241.0 -195370.0) 
                         (list 135830.0 -195370.0) 
                         (list 135830.0 -200303.0) 
                         (list 132779.0 -200303.0) 
                         (list 132779.0 -195370.0) 
                         (list 134241.0 -195370.0) 
                         (list 134241.0 -196347.0) 
                         (list 133950.0 -196347.0) 
                         (list 133915.0 -196352.0) 
                         (list 133882.0 -196365.0) 
                         "c"
         )
        (command "pline" (list 135830.0 -198004.0) "w" 0 0 
                         (list 135830.0 -195370.0) 
                         (list 140009.0 -195370.0) 
                         (list 140009.0 -200303.0) 
                         (list 135830.0 -200303.0) 
                         (list 135830.0 -198004.0) 
                         (list 136591.0 -198004.0) 
                         (list 136591.0 -199210.0) 
                         (list 136596.0 -199246.0) 
                         (list 136609.0 -199278.0) 
                         (list 136631.0 -199307.0) 
                         (list 136659.0 -199328.0) 
                         (list 136692.0 -199342.0) 
                         (list 136727.0 -199347.0) 
                         (list 136762.0 -199342.0) 
                         (list 136795.0 -199328.0) 
                         (list 136824.0 -199307.0) 
                         (list 136845.0 -199278.0) 
                         (list 136859.0 -199246.0) 
                         (list 136864.0 -199210.0) 
                         (list 136864.0 -197061.0) 
                         (list 137513.0 -198362.0) 
                         (list 137532.0 -198390.0) 
                         (list 137557.0 -198413.0) 
                         (list 137586.0 -198428.0) 
                         (list 137618.0 -198436.0) 
                         (list 137652.0 -198436.0) 
                         (list 137684.0 -198428.0) 
                         (list 137714.0 -198413.0) 
                         (list 137739.0 -198390.0) 
                         (list 137757.0 -198362.0) 
                         (list 138407.0 -197061.0) 
                         (list 138407.0 -199210.0) 
                         (list 138412.0 -199246.0) 
                         (list 138425.0 -199278.0) 
                         (list 138447.0 -199307.0) 
                         (list 138475.0 -199328.0) 
                         (list 138508.0 -199342.0) 
                         (list 138543.0 -199347.0) 
                         (list 138579.0 -199342.0) 
                         (list 138612.0 -199328.0) 
                         (list 138640.0 -199307.0) 
                         (list 138661.0 -199278.0) 
                         (list 138675.0 -199246.0) 
                         (list 138680.0 -199210.0) 
                         (list 138680.0 -196483.0) 
                         (list 138675.0 -196448.0) 
                         (list 138661.0 -196415.0) 
                         (list 138640.0 -196387.0) 
                         (list 138612.0 -196365.0) 
                         (list 138579.0 -196352.0) 
                         (list 138543.0 -196347.0) 
                         (list 138506.0 -196352.0) 
                         (list 138472.0 -196367.0) 
                         (list 138443.0 -196391.0) 
                         (list 138421.0 -196422.0) 
                         (list 137635.0 -197996.0) 
                         (list 136849.0 -196422.0) 
                         (list 136831.0 -196395.0) 
                         (list 136806.0 -196372.0) 
                         (list 136777.0 -196357.0) 
                         (list 136745.0 -196348.0) 
                         (list 136712.0 -196348.0) 
                         (list 136680.0 -196355.0) 
                         (list 136651.0 -196371.0) 
                         (list 136626.0 -196392.0) 
                         (list 136607.0 -196420.0) 
                         (list 136595.0 -196451.0) 
                         (list 136591.0 -196483.0) 
                         (list 136591.0 -198004.0) 
                         "c"
         )
        (command "pline" (list 175090.0 -198650.0) "w" 0 0 
                         (list 174716.0 -199025.0) 
                         (list 174001.0 -199025.0) 
                         (list 174001.0 -196570.0) 
                         (list 174716.0 -196570.0) 
                         (list 175090.0 -196945.0) 
                         "c"
         )
        (command "pline" (list 171923.0 -195370.0) "w" 0 0 
                         (list 172938.0 -195370.0) 
                         (list 172938.0 -200303.0) 
                         (list 171018.0 -200303.0) 
                         (list 171018.0 -195370.0) 
                         (list 171923.0 -195370.0) 
                         (list 171923.0 -196298.0) 
                         (list 171594.0 -196298.0) 
                         (list 171558.0 -196302.0) 
                         (list 171526.0 -196316.0) 
                         (list 171497.0 -196338.0) 
                         (list 171476.0 -196366.0) 
                         (list 171462.0 -196399.0) 
                         (list 171457.0 -196434.0) 
                         (list 171462.0 -196469.0) 
                         (list 171476.0 -196502.0) 
                         (list 171497.0 -196530.0) 
                         (list 171526.0 -196552.0) 
                         (list 171558.0 -196566.0) 
                         (list 171594.0 -196570.0) 
                         (list 171911.0 -196570.0) 
                         (list 171911.0 -199025.0) 
                         (list 171594.0 -199025.0) 
                         (list 171558.0 -199030.0) 
                         (list 171526.0 -199043.0) 
                         (list 171497.0 -199065.0) 
                         (list 171476.0 -199093.0) 
                         (list 171462.0 -199126.0) 
                         (list 171457.0 -199161.0) 
                         (list 171462.0 -199197.0) 
                         (list 171476.0 -199230.0) 
                         (list 171497.0 -199258.0) 
                         (list 171526.0 -199279.0) 
                         (list 171558.0 -199293.0) 
                         (list 171594.0 -199298.0) 
                         (list 172502.0 -199298.0) 
                         (list 172538.0 -199293.0) 
                         (list 172570.0 -199279.0) 
                         (list 172599.0 -199258.0) 
                         (list 172620.0 -199230.0) 
                         (list 172634.0 -199197.0) 
                         (list 172639.0 -199161.0) 
                         (list 172634.0 -199126.0) 
                         (list 172620.0 -199093.0) 
                         (list 172599.0 -199065.0) 
                         (list 172570.0 -199043.0) 
                         (list 172538.0 -199030.0) 
                         (list 172502.0 -199025.0) 
                         (list 172184.0 -199025.0) 
                         (list 172184.0 -196570.0) 
                         (list 172502.0 -196570.0) 
                         (list 172538.0 -196566.0) 
                         (list 172570.0 -196552.0) 
                         (list 172599.0 -196530.0) 
                         (list 172620.0 -196502.0) 
                         (list 172634.0 -196469.0) 
                         (list 172639.0 -196434.0) 
                         (list 172634.0 -196399.0) 
                         (list 172620.0 -196366.0) 
                         (list 172599.0 -196338.0) 
                         (list 172570.0 -196316.0) 
                         (list 172538.0 -196302.0) 
                         (list 172502.0 -196298.0) 
                         (list 171923.0 -196298.0) 
                         "c"
         )
        (command "pline" (list 174001.0 -195370.0) "w" 0 0 
                         (list 175637.0 -195370.0) 
                         (list 175637.0 -200303.0) 
                         (list 172938.0 -200303.0) 
                         (list 172938.0 -195370.0) 
                         (list 174001.0 -195370.0) 
                         (list 174001.0 -196298.0) 
                         (list 173410.0 -196298.0) 
                         (list 173375.0 -196302.0) 
                         (list 173342.0 -196316.0) 
                         (list 173314.0 -196338.0) 
                         (list 173292.0 -196366.0) 
                         (list 173279.0 -196399.0) 
                         (list 173274.0 -196434.0) 
                         (list 173279.0 -196469.0) 
                         (list 173292.0 -196502.0) 
                         (list 173314.0 -196530.0) 
                         (list 173342.0 -196552.0) 
                         (list 173375.0 -196566.0) 
                         (list 173410.0 -196570.0) 
                         (list 173728.0 -196570.0) 
                         (list 173728.0 -199025.0) 
                         (list 173410.0 -199025.0) 
                         (list 173375.0 -199030.0) 
                         (list 173342.0 -199043.0) 
                         (list 173314.0 -199065.0) 
                         (list 173292.0 -199093.0) 
                         (list 173279.0 -199126.0) 
                         (list 173274.0 -199161.0) 
                         (list 173279.0 -199197.0) 
                         (list 173292.0 -199230.0) 
                         (list 173314.0 -199258.0) 
                         (list 173342.0 -199279.0) 
                         (list 173375.0 -199293.0) 
                         (list 173410.0 -199298.0) 
                         (list 174773.0 -199298.0) 
                         (list 174808.0 -199293.0) 
                         (list 174841.0 -199279.0) 
                         (list 174869.0 -199258.0) 
                         (list 175323.0 -198803.0) 
                         (list 175345.0 -198775.0) 
                         (list 175358.0 -198742.0) 
                         (list 175363.0 -198707.0) 
                         (list 175363.0 -196889.0) 
                         (list 175358.0 -196853.0) 
                         (list 175345.0 -196821.0) 
                         (list 175323.0 -196792.0) 
                         (list 174869.0 -196338.0) 
                         (list 174841.0 -196316.0) 
                         (list 174808.0 -196302.0) 
                         (list 174773.0 -196298.0) 
                         (list 174001.0 -196298.0) 
                         "c"
         )
        (command "pline" (list 175998.0 -197660.0) "w" 0 0 
                         (list 175998.0 -197798.0) 
                         (list 176003.0 -197833.0) 
                         (list 176017.0 -197866.0) 
                         (list 176038.0 -197894.0) 
                         (list 176067.0 -197916.0) 
                         (list 176099.0 -197929.0) 
                         (list 176135.0 -197934.0) 
                         (list 176170.0 -197929.0) 
                         (list 176203.0 -197916.0) 
                         (list 176231.0 -197894.0) 
                         (list 176253.0 -197866.0) 
                         (list 176266.0 -197833.0) 
                         (list 176271.0 -197798.0) 
                         (list 176271.0 -197343.0) 
                         (list 176266.0 -197308.0) 
                         (list 176253.0 -197275.0) 
                         (list 176231.0 -197247.0) 
                         (list 176203.0 -197225.0) 
                         (list 176170.0 -197212.0) 
                         (list 176135.0 -197207.0) 
                         (list 176099.0 -197212.0) 
                         (list 176067.0 -197225.0) 
                         (list 176038.0 -197247.0) 
                         (list 176017.0 -197275.0) 
                         (list 176003.0 -197308.0) 
                         (list 175998.0 -197343.0) 
                         (list 175998.0 -197660.0) 
                         (list 175637.0 -197660.0) 
                         (list 175637.0 -195370.0) 
                         (list 176634.0 -195370.0) 
                         (list 176634.0 -200303.0) 
                         (list 175637.0 -200303.0) 
                         (list 175637.0 -198450.0) 
                         (list 175998.0 -198450.0) 
                         (list 175998.0 -198707.0) 
                         (list 176003.0 -198742.0) 
                         (list 176017.0 -198775.0) 
                         (list 176038.0 -198803.0) 
                         (list 176067.0 -198825.0) 
                         (list 176099.0 -198839.0) 
                         (list 176135.0 -198843.0) 
                         (list 176170.0 -198839.0) 
                         (list 176203.0 -198825.0) 
                         (list 176231.0 -198803.0) 
                         (list 176253.0 -198775.0) 
                         (list 176266.0 -198742.0) 
                         (list 176271.0 -198707.0) 
                         (list 176271.0 -198252.0) 
                         (list 176266.0 -198217.0) 
                         (list 176253.0 -198184.0) 
                         (list 176231.0 -198156.0) 
                         (list 176203.0 -198134.0) 
                         (list 176170.0 -198121.0) 
                         (list 176135.0 -198116.0) 
                         (list 176099.0 -198121.0) 
                         (list 176067.0 -198134.0) 
                         (list 176038.0 -198156.0) 
                         (list 176017.0 -198184.0) 
                         (list 176003.0 -198217.0) 
                         (list 175998.0 -198252.0) 
                         (list 175998.0 -198450.0) 
                         (list 175637.0 -198450.0) 
                         (list 175637.0 -197660.0) 
                         "c"
         )
        (command "pline" (list 155465.0 -195370.0) "w" 0 0 
                         (list 157805.0 -195370.0) 
                         (list 157805.0 -199105.0) 
                         (list 155465.0 -199105.0) 
                         (list 155465.0 -197469.0) 
                         (list 156449.0 -197469.0) 
                         (list 155876.0 -198328.0) 
                         (list 155862.0 -198357.0) 
                         (list 155857.0 -198389.0) 
                         (list 155861.0 -198421.0) 
                         (list 155874.0 -198451.0) 
                         (list 155895.0 -198476.0) 
                         (list 155922.0 -198494.0) 
                         (list 155953.0 -198503.0) 
                         (list 155985.0 -198504.0) 
                         (list 156016.0 -198495.0) 
                         (list 156044.0 -198478.0) 
                         (list 156066.0 -198454.0) 
                         (list 157580.0 -196180.0) 
                         (list 157593.0 -196153.0) 
                         (list 157599.0 -196123.0) 
                         (list 157596.0 -196092.0) 
                         (list 157585.0 -196064.0) 
                         (list 157567.0 -196039.0) 
                         (list 157544.0 -196020.0) 
                         (list 157515.0 -196008.0) 
                         (list 157485.0 -196004.0) 
                         (list 157449.0 -196010.0) 
                         (list 157416.0 -196027.0) 
                         (list 157391.0 -196054.0) 
                         (list 156449.0 -197469.0) 
                         (list 155465.0 -197469.0) 
                         "c"
         )
        (command "pline" (list 148729.0 -195370.0) "w" 0 0 
                         (list 151105.0 -195370.0) 
                         (list 151105.0 -199105.0) 
                         (list 148729.0 -199105.0) 
                         (list 148729.0 -197178.0) 
                         (list 149625.0 -197178.0) 
                         (list 148896.0 -198273.0) 
                         (list 148882.0 -198302.0) 
                         (list 148877.0 -198334.0) 
                         (list 148881.0 -198366.0) 
                         (list 148894.0 -198395.0) 
                         (list 148915.0 -198420.0) 
                         (list 148942.0 -198438.0) 
                         (list 148973.0 -198448.0) 
                         (list 149005.0 -198448.0) 
                         (list 149036.0 -198440.0) 
                         (list 149064.0 -198423.0) 
                         (list 149085.0 -198399.0) 
                         (list 150600.0 -196125.0) 
                         (list 150614.0 -196097.0) 
                         (list 150619.0 -196067.0) 
                         (list 150616.0 -196037.0) 
                         (list 150606.0 -196008.0) 
                         (list 150588.0 -195983.0) 
                         (list 150564.0 -195964.0) 
                         (list 150536.0 -195952.0) 
                         (list 150506.0 -195948.0) 
                         (list 150469.0 -195954.0) 
                         (list 150436.0 -195972.0) 
                         (list 150411.0 -195999.0) 
                         (list 149625.0 -197178.0) 
                         (list 148729.0 -197178.0) 
                         "c"
         )
        (command "pline" (list -216150.0 216050.0) "w" 0 0 
                         (list -216050.0 216050.0) 
                         (list -216050.0 216150.0) 
                         (list -216150.0 216150.0) 
                         "c"
         )
        (command "pline" (list -216150.0 -216150.0) "w" 0 0 
                         (list -216050.0 -216150.0) 
                         (list -216050.0 -216050.0) 
                         (list -216150.0 -216050.0) 
                         "c"
         )
        (command "pline" (list 216050.0 -216150.0) "w" 0 0 
                         (list 216150.0 -216150.0) 
                         (list 216150.0 -216050.0) 
                         (list 216050.0 -216050.0) 
                         "c"
         )
        (command "pline" (list 216050.0 216050.0) "w" 0 0 
                         (list 216150.0 216050.0) 
                         (list 216150.0 216150.0) 
                         (list 216050.0 216150.0) 
                         "c"
         )
        (command "pline" (list 50.0 216050.0) "w" 0 0 
                         (list 216050.0 216050.0) 
                         (list 216050.0 -216050.0) 
                         (list -216050.0 -216050.0) 
                         (list -216050.0 216050.0) 
                         (list -50.0 216050.0) 
                         (list -50.0 215950.0) 
                         (list -215950.0 215950.0) 
                         (list -215950.0 -215950.0) 
                         (list 215950.0 -215950.0) 
                         (list 215950.0 215950.0) 
                         (list 50.0 215950.0) 
                         "c"
         )
  )

(DEFUN C:mmmb( / );id id_len n m id_c ss dep_x2 dt_id c_date )
  (setvar "osmode" 0)
  (setvar "orthomode" 0)
  (draw_edge)
  (setq id(getstring"请输入流程单号:"))
  (setq id_len(strlen id))
  (setq n 0)
  (setq m 1)
  (while(<= m id_len)
       (setq id_c(substr id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq ss(ssget"w"'(-1374 -2466.47)'(1374 2466.47)))
       (setq dep_x (+ 175259 (* m 2748)))
       (command "move" ss ""  "0,0"  (list dep_x -197836.5)"")
   
       (setq m (+ m 1))
 )
  (setq c_date(getvar "cdate"))
  (setq dt_id (itoa (fix c_date)))
  (setq m 1)
  (while(<= m 4)
       (setq id_c(substr dt_id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq s1(ssget"w"'(-1374 -2466.47)'(1374 2466.47)))
       (command "layer""n""ok""")
       (command "change"s1"""p""la""ok""")
	(scale "ok" ke kf)
        (command "change"s1"""p""la""0""")			    
       (setq dep_x2 (+ 138919 (* m 2180)))
       (command "move" s1 ""   "0,0"  (list dep_x2 -197237.5)"")
       (setq m (+ m 1))
  )
  (setq m 5)
  (while(<= m 6)
       (setq id_c(substr dt_id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq s2(ssget"w"'(-1374 -2466.47)'(1374 2466.47)))
       (command "layer""n""ok""")
       (command "change"s2"""p""la""ok""")
	(scale "ok" ke kf)
        (command "change"s2"""p""la""0""")			    
       (setq dep_x2 (+ 141295 (* m 2180)))
       (command "move" s2 ""   "0,0"  (list dep_x2 -197237.5)"")
       (setq m (+ m 1))
  )
  (setq m 7)
  (while(<= m 8)
       (setq id_c(substr dt_id m 1))
       (if(equal id_c "0")(zero))
       (if(equal id_c "1")(one))
       (if(equal id_c "2")(two))
       (if(equal id_c "3")(three))
       (if(equal id_c "4")(four))
       (if(equal id_c "5")(five))
       (if(equal id_c "6")(six))
       (if(equal id_c "7")(seven))
       (if(equal id_c "8")(eight))
       (if(equal id_c "9")(nine))
       (command "zoom""e""")
       (setq s3(ssget"w"'(-1374 -2466.47)'(1374 2466.47)))
       (command "layer""n""ok""")
       (command "change"s3"""p""la""ok""")
	(scale "ok" ke kf)
        (command "change"s3"""p""la""0""")			    
       (setq dep_x2 (+ 143635 (* m 2180)))
       (command "move" s3 ""   "0,0"  (list dep_x2 -197237.5)"")
       (setq m (+ m 1))
  )
  
  (setq ly_name (getstring"请输入一层有效层名:"))
  (command "layer""n" ly_name "")
  (command "change""all""""p""la" ly_name"""")
  (command "layer""lock"ly_name"")
  (command "clear""")
  (command "layer""unlock"ly_name"")
  (command "zoom""e""")
  (prompt"请再次确认流程单号：")
  (strcat id)
  
 )
(prompt "\n2005-03-21 modified by XifengCheng　！")
(prompt"\n       输入mmms(小边框)运行程序！")
(prompt"\n       输入mmmb(大边框)运行程序！")
