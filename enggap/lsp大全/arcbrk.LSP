(defun get_dt_vl (item dt)
  (cdr (assoc item dt))
)

(defun c:acc ()
    (Setq FLTR (list
		 (cons 0 "arc")
		 )
    )
    (setq ss (ssget "x" FLTR))
    (if	(/= ss nil)
      (progn
	(setq cnt_all (sslength ss))
	(setq cnt 0)
	(while (< cnt cnt_all)
	  (setq ent_name (ssname ss cnt))
	  (setq l_dt (entget ent_name))
	  (if (>= (get_dt_vl 40 l_dt) 50)
	      (setq l_dt (subst	(cons 8 "AA")
				(assoc 8 l_dt)
				l_dt
			 )
		)	    
	  )
	  (entmod l_dt)
	  (setq cnt (1+ cnt))
	)
      )
    )
  )

  (defun c:arcbrk ()
    (Setq FLTR (list
		 (cons 0 "arc")
		 (cons 8 "AA")
	       )
    )
    (setq ss (ssget "x" FLTR))
    (if	(/= ss nil)
      (progn
	(setq p_pt nil)
	(setq cnt_all (sslength ss))
	(setq cnt 0)
	(while (< cnt cnt_all)
	  (setq ent_name (ssname ss cnt))
	  (setq l_dt (entget ent_name))
	  (if (>= (get_dt_vl 40 l_dt) 50)
	    (progn
	      (setq RAD (get_dt_vl 40 l_dt))
	      (setq arf
		     (/	(sqrt
			  (- (* rad rad) (* (- rad 0.0005) (- rad 0.0005)))
			)
			(- rad 0.0005)
		     )
	      )
	      (setq arf (* (atan arf) 2))
	      (setq stt_agl (get_dt_vl 50 l_dt))
	      (setq end_agl (get_dt_vl 51 l_dt))
	      (setq center (get_dt_vl 10 l_dt))
	      (setq arc_agl (- end_agl stt_agl))
	      (if (< arc_agl 0)
		(setq arc_agl (+ arc_agl (* 2 pi)))
	      )
	      (setq n_tmp (fix (/ arc_agl arf)))
	      (setq n_tmp (+ n_tmp 1))
	      (setq m_tmp 0)
	      (while (< m_tmp n_tmp)
		(setq X_tmp (+ (car center)
			       (* (cos (+ stt_agl (* m_tmp arf))) rad)
			    )
		      Y_tmp (+ (cadr center)
			       (* (sin (+ stt_agl (* m_tmp arf))) rad)
			    )
		)
		(setq p_pt (append p_pt (list (list x_tmp y_tmp))))
		(setq m_tmp (1+ m_tmp))
	      ) 
		(setq X_tmp (+ (car center)
			       (* (cos end_agl ) rad)
			    )
		      Y_tmp (+ (cadr center)
			       (* (sin end_agl) rad)
			    )
		)
	      (setq p_pt (append p_pt (list (list x_tmp y_tmp))))
	      
	      (setq pt1 (car p_pt))
	      (setq p_pt (cdr p_pt))
	      (while p_pt
		(setq pt2 (car p_pt))
		(setq p_pt (cdr p_pt))
		(command "line" pt1 pt2 "")
		(setq pt1 pt2)
	      )
	      (setq cnt (1+ cnt))
	    )
	  )
	)
      )
    )
  )
